module vyatta-system-mgmt-routing-instance-v1 {
	namespace "urn:vyatta.com:mgmt:vyatta-system-mgmt-routing-instance:1";
	prefix vyatta-system-mgmt-routing-instance-v1;

	import configd-v1 {
		prefix configd;
	}
	import vyatta-routing-v1 {
		prefix vyatta-routing;
	}
	import vyatta-system-mgmt-v1 {
		prefix system-mgmt;
	}

	organization "Brocade Communications Systems, Inc.";
	contact
		"Brocade Communications Systems, Inc.
		 Postal: 130 Holger Way
			 San Jose, CA 95134
		 E-mail: support@Brocade.com
		 Web: www.brocade.com";


	description
		"Copyright (c) 2016 by Brocade Communications Systems, Inc.
		 All rights reserved.

		 The YANG module for vyatta-system-mgmt-routing-instance-v1";

	revision 2016-04-18 {
		description "Add config-archive to routing-instance.";
	}


	augment /vyatta-routing:routing/vyatta-routing:routing-instance/vyatta-routing:system {
		container config-management {
			configd:help "Configuration management settings";
			uses system-mgmt:cfg-mgt-commit-archive-group;
		}
	}
}
