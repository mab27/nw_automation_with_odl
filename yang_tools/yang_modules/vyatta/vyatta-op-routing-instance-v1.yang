module vyatta-op-routing-instance-v1 {
	namespace "urn:vyatta.com:mgmt:vyatta-op-routing-instance:1";
	prefix vyatta-op-routing-instance-v1;

	import vyatta-routing-v1 {
		prefix routing;
	}
	import vyatta-op-v1 {
		prefix op;
	}

	organization "Brocade Communications Systems, Inc.";
	contact	"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-op-routing-instance-v1-yang to augment
		 'routing-instance' option to vyatta-op's RPCs";

	revision 2016-04-12 {
		description "Initial revision of version 1.";
	}

	grouping routing-instance-option {
		leaf routing-instance {
			type routing:routing-instance-name;
			description "Routing Instance used to qualify the route to a remote object (URI)";
		}
	}

	augment /op:ping/op:input {
		uses routing-instance-option;
	}
}
