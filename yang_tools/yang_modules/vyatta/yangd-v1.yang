module yangd-v1 {
	namespace "urn:vyatta.com:mgmt:yangd:1";
	prefix yangd-v1;

	organization "Brocade Communications Systems, Inc.";
	contact
		"Brocade Communications Systems, Inc.
		 Postal: 130 Holger Way
		 	 San Jose, CA 95134
		 E-mail: support@Brocade.com
		 Web: www.brocade.com";

	description
		"Copyright (c) 2016 by Brocade Communications Systems, Inc.
		 All rights reserved.

		 The YANG module for yangd-v1";

	revision 2016-11-09 {
		description "Initial revision.";
	}

	rpc validate-rpc-input {
		input {
			leaf rpc-namespace {
				type string;
				description "Namespace that the RPC belongs to";
			}
			leaf rpc-model-name {
				type string;
				description "Model name the RPC belongs to";
			}
			leaf rpc-name {
				type string;
				mandatory true;
				description "Name of the RPC";
			}
			leaf rpc-input {
				type string;
				mandatory true;
				description "JSON encoded input to validate for the specified RPC";
			}
		}
		output {
			leaf valid {
				type boolean;
				mandatory true;
				description "Whether the rpc-input is valid";
			}
		}
	}
}
