module vyatta-service-dhcp-relay-routing-instance-v1 {
	namespace "urn:vyatta.com:mgmt:vyatta-service-dhcp-relay-routing-instance:1";
	prefix vyatta-service-dhcp-relay-routing-instance-v1;

	import vyatta-service-dhcp-relay-v1 {
		prefix relay;
	}
	import vyatta-routing-v1 {
		prefix routing;
	}
	import configd-v1 {
		prefix configd;
	}
	import vyatta-interfaces-v1 {
		prefix if;
	}
	import vyatta-interfaces-bridge-v1 {
		prefix if-bridge;
	}
	import vyatta-interfaces-dataplane-v1 {
		prefix if-dataplane;
	}
	import vyatta-interfaces-bonding-v1 {
		prefix if-bonding;
	}
	import vyatta-routing-instance-interfaces-v1 {
		prefix rtintf;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-service-dhcp-relay-routing-instance-v1";

	revision 2016-06-12 {
		description "Initial revision of version 1.";
	}

	augment /routing:routing/routing:routing-instance/routing:service {
		uses relay:dhcp-relay-service {
			refine dhcp-relay {
				configd:end "/opt/vyatta/share/tmplscripts/service/dhcp-relay/configd_vrf_end1.cli";
			}
			refine dhcp-relay/listen-interface {
				configd:allowed "vyatta-show-interfaces.pl --vrf=$VAR(../../../@) --action=dhcp_allowed";
				must "(current() = /if:interfaces/if-dataplane:dataplane/if-dataplane:tagnode)"
					+ "or (substring-after(current(), '.') = /if:interfaces/if-dataplane:dataplane"
					+ "[if-dataplane:tagnode = substring-before(current(), '.')]/if-dataplane:vif/if-dataplane:tagnode)"
					+ "or (current() = /if:interfaces/if-bridge:bridge/if-bridge:tagnode)"
					+ "or (current() = /if:interfaces/if-bonding:bonding/if-bonding:tagnode)"
					+ "or (substring-after(current(), '.') = /if:interfaces/if-bonding:bonding"
					+ "[if-bonding:tagnode = substring-before(current(), '.')]/if-bonding:vif/if-bonding:tagnode)" {
					error-message "listen-interface name must refer to an existing dataplane, bonding or bridge interface name";
				}
				must "current() = /routing:routing/routing:routing-instance" +
					"[routing:instance-name = current()/../../../routing:instance-name]" +
					"/rtintf:interface/rtintf:name" {
					error-message "listen-interface must be configured in this routing instance";
				}
			}
			refine dhcp-relay/upstream-interface {
				configd:allowed "vyatta-show-interfaces.pl --vrf=$VAR(../../../@) --action=dhcp_allowed";
				must "(current() = /if:interfaces/if-dataplane:dataplane/if-dataplane:tagnode)"
					+ "or (substring-after(current(), '.') = /if:interfaces/if-dataplane:dataplane"
					+ "[if-dataplane:tagnode = substring-before(current(), '.')]/if-dataplane:vif/if-dataplane:tagnode)"
					+ "or (current() = /if:interfaces/if-bridge:bridge/if-bridge:tagnode)"
					+ "or (current() = /if:interfaces/if-bonding:bonding/if-bonding:tagnode)"
					+ "or (substring-after(current(), '.') = /if:interfaces/if-bonding:bonding"
					+ "[if-bonding:tagnode = substring-before(current(), '.')]/if-bonding:vif/if-bonding:tagnode)" {
					error-message "listen-interface name must refer to an existing dataplane, bonding or bridge interface name";
				}
				must "current() = /routing:routing/routing:routing-instance" +
					"[routing:instance-name = current()/../../../routing:instance-name]" +
					"/rtintf:interface/rtintf:name" {
					error-message "upstream-interface must be configured in this routing instance";
				}
			}
		}
	}
}
