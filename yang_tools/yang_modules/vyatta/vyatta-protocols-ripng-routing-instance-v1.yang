module vyatta-protocols-ripng-routing-instance-v1 {
	namespace "urn:vyatta.com:mgmt:vyatta-protocols-ripng-routing-instance:1";
	prefix vyatta-protocols-ripng-routing-instance-v1;

	import configd-v1 {
		prefix configd;
	}
	import vyatta-routing-v1 {
		prefix routing-instance;
	}
	import vyatta-protocols-ripng-v1 {
		prefix ripng;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for
		 vyatta-protocols-ripng-routing-instance-v1";

	revision 2016-05-04 {
		description "Initial revision of Routing-instance support";
	}

	augment /routing-instance:routing/routing-instance:routing-instance/routing-instance:protocols {
		uses ripng:ripng-protocol;
	}

	augment /routing-instance:routing/routing-instance:routing-instance/routing-instance:protocols/ripng {
		container log {
			configd:help "RIPNG logging parameters";
			description "RIPNG logging parameters";
			leaf all {
				type empty;
				configd:help "Enable all RIPNG logs";
				description "Enable all RIPNG logs";
				configd:create "/opt/vyatta/share/tmplscripts/protocols/ripng/log/configd_create.sh";
				configd:delete "/opt/vyatta/share/tmplscripts/protocols/ripng/log/configd_delete.sh";
			}
			leaf events {
				type empty;
				configd:help "Enable RIPNG events logs";
				description "Enable RIPNG events logs";
				configd:create "/opt/vyatta/share/tmplscripts/protocols/ripng/log/configd_create.sh";
				configd:delete "/opt/vyatta/share/tmplscripts/protocols/ripng/log/configd_delete.sh";
			}
			uses ripng:ripng-log-packet;
		}
	}
}
