module vyatta-protocols-rib-v1 {
	namespace "urn:vyatta.com:mgmt:vyatta-protocols-rib:1";
	prefix vyatta-protocols-rib-v1;

	import vyatta-protocols-v1 {
		prefix protocols;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2015-2016 by Brocade Communications Systems, Inc.
		 All rights reserved.

		 The YANG module package for vyatta-protocols-rib-v1";

	revision 2016-06-14 {
		description "Updating kernel nsm log delete script.";
	}

	revision 2016-05-02 {
		description "Grouping packet events and all options";
	}

	revision 2015-08-06 {
		description "Initial revision of version 1";
	}

	grouping log-events {
		leaf events {
			type empty;
			configd:help "Enable RIB events logs";
			description "Enable RIB events logs";
			configd:create "/opt/vyatta/share/tmplscripts/protocols/rib/log/configd_create.sh";
			configd:delete "/opt/vyatta/share/tmplscripts/protocols/rib/log/configd_delete.sh";
		}
	}

	grouping log-all {
		leaf all {
			type empty;
			configd:help "Enable all RIB logs";
			description "Enable all RIB logs";
			configd:create "/opt/vyatta/share/tmplscripts/protocols/rib/log/configd_create.sh";
			configd:delete "/opt/vyatta/share/tmplscripts/protocols/rib/log/configd_delete.sh";
		}
	}

	grouping log-packet {
		container packet {
			configd:help "RIB packet logs";
			leaf all {
				type empty;
				configd:help "Enable RIB packet all logs";
				description "Enable RIB packet all logs";
				configd:create "/opt/vyatta/share/tmplscripts/protocols/rib/log/packet/configd_create.sh";
				configd:delete "/opt/vyatta/share/tmplscripts/protocols/rib/log/packet/configd_delete.sh";
			}
			leaf detail {
				type empty;
				configd:help "Enable RIB packet detail logs";
				description "Enable RIB packet detail logs";
				configd:create "/opt/vyatta/share/tmplscripts/protocols/rib/log/packet/configd_create.sh";
				configd:delete "/opt/vyatta/share/tmplscripts/protocols/rib/log/packet/configd_delete.sh";
			}
			leaf send {
				type empty;
				configd:help "Enable RIB packet send logs";
				description "Enable RIB packet send logs";
				configd:create "/opt/vyatta/share/tmplscripts/protocols/rib/log/packet/configd_create.sh";
				configd:delete "/opt/vyatta/share/tmplscripts/protocols/rib/log/packet/configd_delete.sh";
			}
			leaf recv {
				type empty;
				configd:help "Enable RIB packet recv logs";
				description "Enable RIB packet recv logs";
				configd:create "/opt/vyatta/share/tmplscripts/protocols/rib/log/packet/configd_create.sh";
				configd:delete "/opt/vyatta/share/tmplscripts/protocols/rib/log/packet/configd_delete.sh";
			}
		}
	}

	augment /protocols:protocols {
		container rib {
			configd:priority "650";
			configd:help "Routing Information Base (RIB) parameters";
			description "Routing Information Base (RIB) parameters";
			container log {
				configd:help "RIB logging parameters";
				description "RIB logging parameters";
				uses log-all;
				uses log-events;
				leaf nsm {
					type empty;
					configd:help "Enable RIB nsm logs";
					description "Enable RIB nsm logs";
					configd:create "/opt/vyatta/share/tmplscripts/protocols/rib/log/configd_create.sh";
					configd:delete "/opt/vyatta/share/tmplscripts/protocols/rib/log/configd_delete.sh";
				}
				leaf kernel {
					type empty;
					configd:help "Enable RIB kernel logs";
					description "Enable RIB kernel logs";
					configd:create "/opt/vyatta/share/tmplscripts/protocols/rib/log/configd_create.sh";
					configd:delete "/opt/vyatta/share/tmplscripts/protocols/rib/log/configd_delete.sh";
				}
				uses log-packet;
			}			
		}
	}
}
