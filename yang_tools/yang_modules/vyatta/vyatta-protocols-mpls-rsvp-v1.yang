module vyatta-protocols-mpls-rsvp-v1 {
	namespace "urn:vyatta.com:mgmt:vyatta-protocols-mpls-rsvp:1";
	prefix protocols-mpls-rsvp;

	import vyatta-types-v1 {
		prefix types;
	}
	import vyatta-protocols-v1 {
		prefix protocols;
	}
	import vyatta-protocols-interface-validation-mpls-v1 {
		prefix if-validation;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2015-2016 by Brocade Communications Systems, Inc.
		 All rights reserved." +

		"YANG data module for MPLS-TE and RSVP-TE configuration";

	revision 2015-06-05 {
		description "Initial revision.";
	}

	/* MPLS-TE type definitions */
	typedef admin-group-name {
		type string {
			length "1..14";
		}
	}

	typedef affinity-usage-type {
		type enumeration {
			enum include-any {
				description "The set of attribute filters associated with a tunnel any of which must be present for a link to be acceptable";
				configd:help "Include any attribute";
			}
			enum exclude-any {
				description "The set of attribute filters associated with a tunnel any of which renders a link unacceptable";
				configd:help "Exclude any attribute";
			}
		}
	}

	typedef bandwidth-suffix {
		type string {	/* Number followed by suffix */
			pattern '([1-9][0-9]{0,9}|10000000000|([1-9][0-9]{0,6}|10000000)[Kk]|([1-9][0-9]{0,3}|10000)[Mm]|([1-9]|10)[Gg])';
			configd:pattern-help "<number>[<suffix(k,m,g)>] in range 1..10g";
		}
	}

	typedef frr-protection-type {
		type enumeration {
			enum one-to-one {
				configd:help "One-to-One protection mechanism";
			}
		}
		default "one-to-one";
	}

	typedef hop-action-type {
		type enumeration {
			enum strict {
				configd:help "Strict hop";
			}
			enum loose {
				configd:help "Loose hop";
			}
		}
		default "loose";
	}

	typedef explicit-path-name {
		type string {
			length "1..256";
		}
	}

	typedef tunnel-name {
		type string {
			length "1..256";
		}
	}

	/* Global groupings */
	grouping admin-groups {
		list admin-groups {
			description "List of named TE admin-groups";
			configd:help "List of named TE admin-groups";
			key "name";
			leaf name {
				description "A string name that uniquely identifies a TE admin-group";
				type admin-group-name {
					configd:help "Name of the admin-group";
				}
			}
			leaf value {
				mandatory true;
				description "Value of the admin-group";
				configd:help "Value of the admin-group";
				type uint32 {
					range "0..31";
				}
			}
		}
	}

	grouping explicit-route-objects {
		list explicit-route-objects {
			key "index";
			description "List of explicit route objects";
			configd:help "List of explicit route objects";
			leaf index {
				type uint8 {
					configd:help "Index of explicit route object";
				}
			}
			leaf address {
				configd:help "An IP hop address";
				type types:ipv4-address;
			}
			leaf action {
				configd:help "An IP hop action";
				type hop-action-type;
			}
		}
	}

	grouping explicit-paths {
		description "Global explicit path grouping";
		list explicit-paths {
			configd:help "List of explicit paths";
			key "name";
			leaf name {
				description "A string name that uniquely identifies an explicit path";
				type explicit-path-name {
					configd:help "Explicit path name";
				}
			}

			uses explicit-route-objects;
		}
	}

	grouping reoptimization {
		description "Global periodic LSP reoptimization parameters.";
		container reoptimization {
			presence "Enable TE tunnel reoptimization globally on the node.";
			configd:help "Enable TE tunnel reoptimization";
			leaf interval {
				description "Periodic reoptimization interval in seconds.";
				configd:help "Periodic reoptimization interval in seconds";
				type uint32 {
					range "0..604800";
				}
				default "3600";
			}
		}
	}

	grouping tail-signaling {
		description "Signaling properties for LSP tail-end.";
		container tail-signaling {
			configd:help "Signaling properties for LSP tail-end";
			leaf explicit-null {
				configd:help "Send Explicit NULL Label";
				type empty;
			}
		}
	}

	/* Tunnel groupings */
	grouping path-affinities {
		description "Path affinities grouping";
		container affinities {
			description "Path affinities container";
			configd:help "Path affinities";
			list constraints {
				key "usage";
				configd:help "List of affinity constraints";
				leaf usage {
					type affinity-usage-type;
				}
				list affinity-names {
					description "List of affinities";
					configd:help "List of affinity names";
					key "name";
					leaf name {
						type leafref {
							path "/protocols:protocols/protocols-mpls-rsvp:mpls-rsvp/protocols-mpls-rsvp:globals/protocols-mpls-rsvp:admin-groups/protocols-mpls-rsvp:name";
						}
					}
				}
			}
		}
	}

	grouping path-selection {
		container path-selection {
			configd:help "Path selection properties";
			leaf hop-limit {
				configd:help "The tunnel path hop limit";
				type uint8 {
					range "1..255";
				}
			}
			uses path-affinities;
		}
	}

	grouping lsp-signaling-properties {
		description "LSP signaling properties.";
		leaf bandwidth {
			type bandwidth-suffix;
			configd:help "Bandwidth to be reserved (bps) <1-10000000000>";
		}
		container priority {
			description "Sets the setup/hold priority to use in the session attribute object.";
			configd:help "Priority to use in the session attribute object";
			must "setup >= hold" {
				error-message "Setup priority cannot be higher (nearer 0) than hold priority";
			}
			leaf setup {
				description "RSVP session attributes setup priority";
				configd:help "Value for setup priority";
				type uint8 {
					range "0..7";
				}
				default "7";
			}
			leaf hold {
				description "RSVP session attributes hold priority";
				configd:help "Value for hold priority";
				type uint8 {
					range "0..7";
				}
				default "0";
			}
		}
	}

	grouping recording {
		container record-route {
			description "Path recording";
			configd:help "Requests path RRO recording in RSVP PATH message";
			leaf disable {
				configd:help "Disable path RRO recording in RSVP PATH message";
				type empty;
			}
			leaf record-label {
				configd:help "Record labels exchanged by all peers";
				type empty;
			}
		}
	}

	grouping routing-properties {
		container autoroute-announce {
			presence "Enable autoroute announce.";
			description "Announce the TE tunnel as autoroute to IGP for use as IGP shortcut.";
			configd:help "Announce the tunnel for IGP shortcut use";
			leaf relative-metric {
				description "Relative TE metric to use when announcing the tunnel as shortcut";
				configd:help "Relative metric";
				type int32 {
					range "-65535..65535";
				}
			}
			leaf absolute-metric {
				description "Absolute TE metric to use when announcing the tunnel as shortcut";
				configd:help "Absolute metric";
				must "not(../relative-metric)" {
					error-message "Absolute-metric and relative-metric are mutually exclusive";
				}
				type uint32 {
					range "1..65535";
				}
			}
		}
	}

	grouping fast-reroute {
		container fast-reroute {
			presence "FRR local protection is desired";
			configd:help "Requests FRR local protection on LSRs";
			leaf node-protection-desired {
				description "Request FRR node protection on LSRs if present.";
				configd:help "Request FRR node protection on LSRs";
				type empty;
			}

			leaf protection {
				configd:help "LSP Protection mechanism";
				type frr-protection-type;
			}

			uses lsp-signaling-properties;
			uses path-selection;
		}
	}

	grouping tunnel-path-params {
		description "Tunnel path properties grouping";
		leaf lockdown  {
			type empty;
			description "Indicates no reoptimization to be attempted for this path.";
			configd:help "Do not reoptimize this path";
		}
	}

	/* Interface groupings */
	grouping bandwidth-constraints {
		container bandwidth-constraints {
			configd:help "Bandwidth constraints";
			leaf maximum-reservable {
				type bandwidth-suffix;
				configd:help "Maximum reservable bandwidth (bps) <1-10000000000>";
			}
		}
	}

	grouping interface-attributes {
		description "Interface TE properties grouping.";
		leaf te-metric {
			configd:help "Interface TE metric";
			type uint32 {
				range "1..65535";
			}
		}
		list admin-groups {
			key admin-group;
			configd:help "List of named admin-group entries";
			leaf admin-group {
				type leafref {
					path "/protocols:protocols/protocols-mpls-rsvp:mpls-rsvp/protocols-mpls-rsvp:globals/protocols-mpls-rsvp:admin-groups/protocols-mpls-rsvp:name";
				}
			}
		}
	}

	grouping rsvp-signaling {
		container signaling {
			configd:help "RSVP signaling properties";
			container hello {
				configd:help "Configure Hello parameters";
				leaf interval {
					type uint32 {
						range "10..65535";
					}
					configd:help "Interval between successive Hello packets in milliseconds";
				}
				leaf receipt {
					type empty;
					configd:help "Enable the exchange of Hello messages";
				}
				leaf timeout {
					type uint32 {
						range "10..65535";
					}
					configd:help "Timeout value in milliseconds";
				}
			}
			container refresh {
				configd:help "Configure refresh parameters";
				leaf interval {
					configd:help "Interval in seconds between successive refreshes";
					type uint32 {
						range "1..65535";
					}
				}
				container reduction {
					configd:help "Configure RSVP Refresh Reduction parameters";
					leaf disable {
						configd:help "Disable refresh reduction";
						type empty;
					}
				}
			}
		}
	}

	/* Protocols augmentation */
	augment /protocols:protocols {
		container mpls-rsvp {
			presence "Enable MPLS RSVP Traffic Engineering";
			configd:priority "640";
			configd:help "MPLS RSVP Traffic Engineering";
			configd:validate "vyatta-mpls-rsvp.pl --check-params";
			configd:end "vyatta-mpls-rsvp.pl --proto";

			/* Global configuration data */
			container globals {
				description "Configuration data model for Global System-wide MPLS Traffic Engineering.";
				configd:help "Global configuration";

				uses admin-groups;
				uses explicit-paths;
				uses reoptimization;
				uses tail-signaling;
			}

			/* Interface configuration data */
			container interfaces {
				description "Configuration data model for TE interfaces.";
				configd:help "Interface configuration";

				list interface {
					configd:help "List of interfaces";
					configd:end "vyatta-mpls.pl --dev=$VAR(@)";
					key "interface";
					uses if-validation:interface-mpls;
					uses bandwidth-constraints;
					uses interface-attributes;
					uses rsvp-signaling;
				}
			}

			/* Neighbor configuration data */
			container neighbors {
				description "RSVP neighbors container";
				configd:help "RSVP neighbor configuration";
				list neighbor {
					key "address";
					configd:help "List of RSVP neighbors";
					leaf address {
						type types:ipv4-address;
						configd:help "Neighbor address";
					}
				}
			}

			container tunnels {
				description "Configuration data model for TE tunnels.";
				configd:help "Tunnel configuration";

				list tunnel {
					description "TE tunnel.";
					configd:help "List of TE tunnels";
					key "name";
					leaf name {
						type tunnel-name {
							configd:help "TE tunnel name";
						}
					}

					leaf destination {
						configd:help "Specify tunnel egress";
						type types:ipv4-address;
					}

					leaf source {
						configd:help "Specify tunnel ingress";
						type types:ipv4-address;
					}

					uses routing-properties;

					container primary {
						configd:help "Configure primary LSP option";
						leaf explicit-path {
							configd:help "Name of explicit path to be used";
							type leafref {
								path "../../../../globals/explicit-paths/name";
							}
						}
						uses fast-reroute;
						uses lsp-signaling-properties;
						uses path-selection;
						uses recording;
						uses tunnel-path-params;
					}

					container secondary {
						presence "Enable secondary LSP";
						configd:help "Configure secondary LSP option";
						leaf explicit-path {
							configd:help "Name of explicit path to be used";
							type leafref {
								path "../../../../globals/explicit-paths/name";
							}
						}
						uses lsp-signaling-properties;
						uses path-selection;
						uses recording;
						uses tunnel-path-params;
					}
				}
			}

			container log {
				configd:help "RSVP logging parameters";
				leaf cspf {
					type empty;
					configd:help "Enable RSVP CSPF logs";
				}
				leaf events {
					type empty;
					configd:help "Enable RSVP events logs";
				}
				container fsm {
					configd:help "RSVP FSM logs";
					leaf egress {
						type empty;
						configd:help "Enable RSVP Egress FSM logs";
					}
					leaf ingress {
						type empty;
						configd:help "Enable RSVP Ingress FSM logs";
					}
					container transit {
						configd:help "RSVP Transit FSM logs";
						leaf downstream {
							type empty;
							configd:help "Enable RSVP Transit Downstream FSM logs";
						}
						leaf upstream {
							type empty;
							configd:help "Enable RSVP Transit Upstream FSM logs";
						}
					}
				}
				leaf nsm {
					type empty;
					configd:help "Enable RSVP NSM logs";
				}
				leaf packet {
					type empty;
					configd:help "Enable RSVP packet logs";
				}
				leaf rib {
					type empty;
					configd:help "Enable RSVP RIB logs";
				}
			}
		}
	}
}
