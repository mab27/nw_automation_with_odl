module vyatta-protocols-msdp-v1 {
	namespace "urn:vyatta.com:mgmt:vyatta-protocols-msdp:1";
	prefix vyatta-protocols-msdp-v1;

	import vyatta-types-v1 {
		prefix types;
	}
	import vyatta-protocols-v1 {
		prefix protocols;
	}
	import configd-v1 {
		prefix configd;
	}
	import vyatta-policy-v1 {
		prefix policy;
	}
	import vyatta-policy-route-v1 {
		prefix policy-route;
	}

	organization "Brocade Communications Systems, Inc.";
	contact
		"Brocade Communications Systems, Inc.
		 Postal: 130 Holger Way
		         San Jose, CA 95134
		 E-mail: support@Brocade.com
		 Web: www.brocade.com";

	description
		"Copyright (c) 2015-2016 by Brocade Communications Systems, Inc.
		 All rights reserved.

		 The YANG module for vyatta-protocols-msdp-v1";

	revision 2016-07-27 {
		description "Add SA-holdtime to allow control of waiting time before discarding stale SA messages
		Add SA-limit to allow control of maximum number of SA messages cached by a particular peer
		Add SA-cache to allow control of SA message cache size";
	}

	revision 2016-03-16 {
		description "Add leafrefs and must statements to replace local-only validation";
	}
	revision 2015-07-28 {
		description "Initial revision, replacing vyatta-protocols-msdp";
		configd:migration 1;
	}

	typedef prefix-list-name {
		type leafref {
			path "/policy:policy/policy-route:route/policy-route:prefix-list/policy-route:tagnode";
		}
	}

	// TODO this could/should be provided in vyatta-types
	typedef non-loop-ipv4-address {
		type types:ipv4-address {
			pattern '(([0-9]|[1-9][0-9]|1([0-13-9][0-9]|2[0-68-9])|2[0-4][0-9]|25[0-5])\.).+';
			configd:help "IPv4 Address, except localhost";
			configd:pattern-help "!<127.x.x.x>";
		}
	}

	grouping filter-lists {
		leaf access-list {
			type uint32 {
				range "100..199 | 2000..2699";
			}
			must "current() = /policy:policy/policy-route:route/policy-route:access-list/policy-route:tagnode" {
				error-message "access-list has not been configured";
			}
			configd:allowed "/opt/vyatta/share/tmplscripts/protocols/msdp/access-list_allowed.sh";
		}
		leaf rp-list {
			type prefix-list-name;
		}
	}

	grouping export-grouping {
		container export {
			uses filter-lists {
				refine access-list {
					configd:help "Filter cache entry advertisements by (S,G)";
				}
				refine rp-list {
					configd:help "prefix-list filtering cache entry advertisements by RP address";
				}
			}
		}
	}
	
	grouping import-grouping {
		container import {
			uses filter-lists {
				refine access-list {
					configd:help "Filter creation of cache entries by (S,G)";
				}
				refine rp-list {
					configd:help "prefix-list filtering cache entry creation by RP address";
				}
			}
		}
	}

	/*
	 * This grouping is not intended for use outside of this model as it
	 * contains a leafref which uses a relative path.
	 */
	grouping peer-list {
		leaf-list peer {
			ordered-by "user";
			configd:help "IP address of a peer in the group";
			type leafref {
				path "../../peer/address";
			}
		}
	}
	
	// The common parameters for both peer and peer-group configuration
	grouping common-peer-parameters {
		leaf holdtime {
			type uint32 {
				range 3..75;
			}
			configd:help "Wait time for keep alive messages before declaring the peer down";
		}
		leaf connect-retry {
			type uint32 {
				range 1..60;
			}
			configd:help "Period between attempts to re-establish peer connection";
		}
		leaf shutdown {
			type empty;
			configd:help "Administratively shut down the peer";
		}
		leaf keepalive {
			type uint32 {
				range 1..60;
			}
			configd:help "Period at which keep alive messages will be sent";
		}
		leaf sa-limit {
			type uint32 {
				range 0..10000;
			}
			configd:help "Maximum number of cached SA messages";
			description
				"The value of sa-limit sets a limit to the maximum number of SA messages cached for a particular peer.
				When the limit is reached any further messages received are discarded until the current total is reduced.
				The default value is set at the cache limit (for all peers).";
		}
		uses export-grouping;
		uses import-grouping;
	}

	grouping msdp-parameters {
		container msdp {
			configd:priority 790;
			configd:help "Multicast Source Discovery Protocol (MSDP)";
			list peer {
				configd:help "Configure an MSDP peer";
				key "address";
				unique "default-peer/priority";
				leaf address {
					type non-loop-ipv4-address;
				}
			
				uses common-peer-parameters {
					refine holdtime {
						default 75;
					}
					refine connect-retry {
						default 30;
					}
					refine keepalive {
						default 60;
					}
					refine sa-limit {
					        default 10000;
					}
					refine export {
						configd:help "Configure which (S,G)s will be advertised to the peer";
					}
					refine import {
						configd:help "Configure which (S,G)s which will be accepted from the peer";
					}
				}
				
				container default-peer {
					presence "Peer is configured as a default";
					configd:help "Skip RPF check for SA messages from this peer";
					leaf priority {
						type uint32 {
							range 1..2000;
						}
						configd:help "Configure priority for default peer";
					}
					leaf prefix-list {
						type prefix-list-name;
						configd:help "Specify RP prefixes that the peer will be default for";
					}
				}
				
				leaf local-address {
					type non-loop-ipv4-address;
					must "current() != ../address" {
						error-message "local-address cannot be the same as the peer address";
					}
					configd:help "IPv4 address used for the connection to the MSDP peer";
				}
				
				leaf password {
					type string {
						length 1..80;
					}
					configd:secret "true";
					configd:help "Password for the peer";
				}
			}
			
			
			list peer-group {
				configd:help "Configure an MSDP peer-group (peers share common parameters)";
				key "name";
				leaf name {
					type string;
				}
				uses peer-list {
					refine peer {
						must "count(../../peer-group/peer[. = current()]) = 1" {
							error-message "A peer cannot be a member of multiple peer-groups";
						}
					}
				}
				
				// Refine the help messages so they are correct for a peer group
				uses common-peer-parameters {
					refine holdtime {
						configd:help "Wait time for keep alive messages before declaring a peer down";
					}
					refine shutdown {
						configd:help "Administratively shut down all peers in the group";
					}
					refine export {
						configd:help "Configure which (S,G)s will be advertised to members of the peer group";
					}					
					refine import {
						configd:help "Configure which (S,G)s which will be accepted from members of the peer group";
					}
				}
			}
			
			uses export-grouping {
				refine export {
					configd:help "Configure which (S,G)s may be advertised to any peer";
				}
			}
			uses import-grouping {
				refine import {
					configd:help "Configure which (S,G)s may be accepted from any peer";
				}
			}
			leaf originated-id {
				type non-loop-ipv4-address;
				configd:help "Override RP address sent in SA messages";
			}
			
			list mesh-group {
				configd:help "Configure MSDP peers to be members of a mesh group";
				key "name";
				leaf name {
					type string;
				}
				uses peer-list {
					refine peer {
						min-elements 1;
					}
				}
			}
			
			leaf-list log {
				configd:help "Configure MSDP logging";
				type enumeration {
					enum all {
						configd:help "Enable all logs";
					}
					enum bgp {
						configd:help "Enable bgp logs";
					}
					enum cache {
						configd:help "Enable cache logs";
					}
					enum events {
						configd:help "Enable events logs";
					}
					enum fsm {
						configd:help "Enable fsm logs";
					}
					enum other {
						configd:help "Enable other logs";
					}
					enum packet {
						configd:help "Enable packet logs";
					}
					enum pim {
						configd:help "Enable pim logs";
					}
					enum rpfcheck {
						configd:help "Enable rpfcheck logs";
					}
					enum snmp {
						configd:help "Enable snmp logs";
					}
				}
			}

			leaf sa-holdtime {
				type uint32 {
					range 63..600;
				}

				configd:help "Wait time for refresh of SA messages before discarding";
				description
					"Cached SA messages are held
					for a period of time before
					being discarded if not
					refreshed by a peer.  Peer
					refresh period for SA
					messages,
					'SA-Advertisement-Period', is
					60 seconds.
					The minimum value for
					'sa-holdtime' must be greater
					than 'SA-Advertisement-Period'
					plus an additional
					'SA-Hold-Down-Period'.
					The value of 'sa-holdtime'
					should be carefully chosen to
					avoid frequent flooding of the
					network with SA
					advertisements";
				default "240";
			}

			leaf sa-cache {
				type uint32 {
					range 1..10000;
				}
				configd:help "Configure maximum number of cached SA messages";
				description
					"SA messages are held in a cache for a period of time before being discarded if 
					not refreshed by a peer.
					The value of 'sa-cache' should be chosen to trade off memory usage whilst 
					avoiding frequent flooding of the network with SA advertisements due to cache 
					misses";
				default "10000";
			}
		}
	}

	augment /protocols:protocols {
		uses msdp-parameters {
			refine msdp {
				configd:validate "vyatta-msdp-validate";
				configd:end "vyatta-msdp-configure";
			}
			refine msdp/peer {
				configd:validate "vyatta-msdp-validate -- --level peer --param $VAR(@)";
			}
		}
	}

}
