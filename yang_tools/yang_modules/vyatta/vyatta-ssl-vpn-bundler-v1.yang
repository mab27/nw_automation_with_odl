module vyatta-ssl-vpn-bundler-v1 {
	namespace "urn:vyatta.com:mgmt:vyatta-ssl-vpn-bundler:1";
	prefix vyatta-ssl-vpn-bundler-v1;

	import vyatta-interfaces-v1 {
		prefix if;
	}
	import vyatta-interfaces-openvpn-v1 {
		prefix interfaces-openvpn;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	revision 2015-08-14 {
		description "Initial revision of version 1.";
	}


	augment /if:interfaces/interfaces-openvpn:openvpn {
		container client-bundle {
			presence "true";
			configd:help "Generate SSL-VPN Client Bundles";
			leaf osx {
				type empty;
				configd:help "Generate OpenVPN formatted config file for OS X OpenVPN clients";
			}
			leaf linux {
				type empty;
				configd:help "Generate SSL-VPN Client Bundle for Linux";
			}
			leaf windows {
				type empty;
				configd:help "Generate SSL-VPN Client Bundle for Windows";
			}
			leaf generic {
				type empty;
				configd:help "Generate standard OpenVPN formatted config file with CA certificate inline";
			}
		}
	}
}
