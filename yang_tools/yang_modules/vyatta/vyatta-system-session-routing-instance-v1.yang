module vyatta-system-session-routing-instance-v1 {
	namespace "urn:vyatta.com:mgmt:vyatta-system-session-routing-instance:1";
	prefix vyatta-system-session-routing-instance-v1;

	import vyatta-routing-v1 {
		prefix routing;
	}
	import vyatta-system-session-v1 {
		prefix system-session;
	}
	import configd-v1 {
		prefix configd;
	}

	organization "Brocade Communications Systems, Inc.";
	contact
		"Brocade Communications Systems, Inc.
		 Postal: 130 Holger Way
			 San Jose, CA 95134
		 E-mail: support@Brocade.com
		 Web: www.brocade.com";

	description
		"Copyright (c) 2016 by Brocade Communications Systems, Inc.
		 All rights reserved.

		 YANG module for Vyatta firewall session configuration and operation
		 for routing instances.";

	revision 2016-06-17 {
		description "Initial revision.";
	}

	augment /routing:routing/routing:routing-instance/routing:system {
		container session {
			description "Configure timeouts for session";
			configd:help "Configure timeouts for session";
			uses system-session:timeout-group;
		}
	}
}
