module vyatta-service-dns-v1 {
	namespace "urn:vyatta.com:mgmt:vyatta-service-dns:1";
	prefix vyatta-service-dns-v1;

	import vyatta-types-v1 {
		prefix types;
	}
	import vyatta-services-v1 {
		prefix service;
	}
	import vyatta-interfaces-v1 {
		prefix if;
	}
	import configd-v1 {
		prefix configd;
	}
	import vyatta-system-v1 {
		prefix system;
	}
	import vyatta-system-network-v1 {
		prefix sys-net;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 DNS configuration";

	revision 2016-08-24 {
		description "Support IPv6 address for name-server.";
	}

	revision 2016-04-18 {
		description "Grouping services and XPATH optimizations.";
	}

	revision 2015-08-14 {
		description "Initial revision of version 1.";
	}

	grouping dns-service-forwarding {
		container forwarding {
			presence "Enable DNS forwarding";
			description "DNS forwarding for relaying the queries";
			configd:priority "918";
			configd:help "DNS forwarding";
			configd:end "/opt/vyatta/share/tmplscripts/service/dns/forwarding/configd_end.sh";
			leaf-list dhcp {
				type string;
				ordered-by "user";
				configd:help "Use nameservers received from DHCP server for specified interface";
				configd:allowed "/opt/vyatta/share/tmplscripts/service/dns/forwarding/dhcp/configd_allowed.sh";
				must "(/if:interfaces/*/*[local-name(.) = 'tagnode']"
					+ "[. = current()]/../*[local-name(.) = 'address'][. = 'dhcp'])"
					+ " or "
					+ "(/if:interfaces/*/*[local-name(.) = 'vif']"
					+ "[./../* = substring-before(current(), '.')]"
					+ "/*[local-name(.) = 'tagnode']"
					+ "[. = substring-after(current(), '.')]"
					+ "/../*[local-name(.) = 'address'][. = 'dhcp'])" {
						error-message "Interface must exist, and have DHCP address.";
					}
				}
			leaf cache-size {
				type uint32 {
					range 0..10000;
				}
				default "150";
				configd:help "DNS forwarding cache size";
			}
			leaf-list listen-on {
				type string;
				min-elements "1";
				ordered-by "user";
				configd:help "Interface to listen for DNS queries [REQUIRED]";
				configd:allowed "/opt/vyatta/share/tmplscripts/service/dns/forwarding/listen-on/configd_allowed.sh";
				// Generates warning if interface doesn't exist 
				// Can't generate error as this might invalidate
				// previous configurations.
				configd:validate "/opt/vyatta/share/tmplscripts/service/dns/forwarding/listen-on/configd_validate1.cli";
			}
			leaf-list name-server {
				type union {
					type types:ipv4-address;
					type types:ipv6-address;
				}
				ordered-by "user";
				configd:help "DNS server to forward queries";
			}
			leaf system {
				type empty;
				configd:help "DNS forwarding to system nameservers";
			}
			list domain {
				configd:help "DNS domain to forward to a local server";
				key "tagnode";
				leaf tagnode {
					type string;
					configd:help "DNS domain to forward to a local server";
				}
				leaf server {
					type types:ipv4-address;
					mandatory true;
					configd:help "DNS server to forward queries";
				}
			}
		}
	}

	grouping dns-service-dynamic {
		container dynamic {
			presence "Enable DNS Dynamic Sync";
			description "DNS dynamic for syncing address change";
			configd:priority "919";
			configd:help "Dynamic DNS";
			list interface {
				configd:help "Interface to send DDNS updates for";
				configd:allowed "/opt/vyatta/share/tmplscripts/service/dns/dynamic/interface/configd_allowed.sh";
				configd:end "/opt/vyatta/share/tmplscripts/service/dns/dynamic/interface/configd_end.sh";
				// Generates warning if interface doesn't exist 
				// Can't generate error as this might invalidate
				// previous configurations.
				configd:validate "/opt/vyatta/share/tmplscripts/service/dns/dynamic/interface/configd_validate2.cli";
				key "tagnode";
				leaf tagnode {
					type string;
					configd:help "Interface to send DDNS updates for";
					configd:allowed "/opt/vyatta/sbin/vyatta-interfaces.pl --show all";
				}
				list service {
					min-elements "1";
					configd:help "Service being used for Dynamic DNS";
					configd:allowed "/opt/vyatta/share/tmplscripts/service/dns/dynamic/interface/service/configd_allowed.sh";
					key "tagnode";
					leaf tagnode {
						type string {
							pattern '(dnspark|dslreports|dyndns|easydns|namecheap|sitelutions|zoneedit)' {
								error-message "
Allowed values: dnspark dslreports dyndns easydns namecheap sitelutions zoneedit";
							}
						}
						configd:help "Service being used for Dynamic DNS";
						configd:allowed "/opt/vyatta/share/tmplscripts/service/dns/dynamic/interface/service/configd_allowed.sh";
					}
					leaf password {
						type string;
						mandatory true;
						configd:secret "true";
						configd:help "Password for DDNS service";
					}
					leaf login {
						type string;
						mandatory true;
						configd:help "Login for DDNS service";
					}
					leaf server {
						type string;
						configd:help "Server to send DDNS update to (IP address|hostname)";
					}
					leaf-list host-name {
						type string;
						min-elements "1";
						ordered-by "user";
						configd:help "Hostname registered with DDNS service";
					}
				}
			}
		}
	}

	augment /service:service {
		container dns {
			presence "Enable service DNS for default instance";
			description "Dns service in default vrf";
			configd:help "Domain Name Server (DNS) parameters";
			uses dns-service-forwarding{
				refine forwarding/system {
					must "/system:system/sys-net:name-server" {
						error-message
                                                	"No name-servers set under 'system name-server";
					}
				}
			}
			uses dns-service-dynamic;
		}
	}
}
