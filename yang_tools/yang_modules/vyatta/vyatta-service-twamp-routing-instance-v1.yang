module vyatta-service-twamp-routing-instance-v1 {
	namespace "urn:vyatta.com:mgmt:vyatta-service-twamp-routing-instance:1";
	prefix vyatta-service-twamp-routing-instance-v1;

	import configd-v1 {
		prefix configd;
	}
	import vyatta-routing-v1 {
		prefix routing;
	}
	import vyatta-service-twamp-v1 {
		prefix twamp;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 Routing Instance support for TWAMP server configuration and
		 twping RPC.";

	revision 2016-04-14 {
		description "Initial revision, with routing instance support for TWAMP";
	}

	augment /twamp:twping/twamp:input {
		leaf routing-instance {
			description "The routing instance context for this session";
			type routing:routing-instance-name;
			default "default";
		}
	}

	augment /routing:routing/routing:routing-instance/routing:service {
		uses twamp:twamp-parameters {
			refine twamp/server {
				must "../../../routing:instance-type = 'vrf'" {
					error-message "TWAMP is only supported for routing instances " +
						"with an instance-type of 'vrf'";
				}
				configd:end "twampd-config.pl --routing-instance $VAR(../../../@)";
			}
		}
	}
}
