module vyatta-routing-v1 {
	namespace "urn:vyatta.com:mgmt:vyatta-routing-v1:1";
	prefix vyatta-routing-v1;

	import vyatta-types-v1 { prefix types; }

	import configd-v1 { prefix configd; }

	organization "Brocade Communications Systems, Inc.";
	contact
		"Brocade Communications Systems, Inc.
		 Postal: 130 Holger Way
			 San Jose, CA 95134
		 E-mail: support@Brocade.com
		 Web: www.brocade.com";

	description
		"Copyright (c) 2016 by Brocade Communications Systems, Inc.
		 All rights reserved.

		 Routing Instance configuration";

	revision 2016-06-28 {
		description "Addition of routing-instance typedefs and groups: " +
			    "routing-instance-ref, routing-instance-name, " +
			    "routing-instance-list, routing-instance-leaf " +
			    "and routing-instance-or-default-leaf.";
	}

	revision 2016-02-01 {
		description "Initial revision of version 1.";
	}

	typedef routing-instance-ref {
		type leafref {
			path "/routing/routing-instance/instance-name";
		}
	}

	typedef routing-instance-name {
		description "A Routing Instance name";
		type types:alpha-numeric {
			length "1..16";
		}
	}

	grouping routing-instance-list {
		list routing-instance {
			description "A list of Routing Instances";
			configd:help "Routing Instance";
			key instance-name;
			leaf instance-name {
				description "Routing Instance name";
				type routing-instance-ref;
			}
		}
	}

	grouping routing-instance-leaf {
		leaf routing-instance {
			description "A Routing Instance";
			type routing-instance-ref;
			configd:help "Routing Instance";
		}
	}

	grouping routing-instance-or-default-leaf {
		leaf routing-instance {
			description "A Routing Instance name, or 'default'";
			type union {
				type routing-instance-name;
				type enumeration {
					enum default;
				}
			}
			must "(current() = /vyatta-routing-v1:routing/vyatta-routing-v1:routing-instance/vyatta-routing-v1:instance-name) or (current() = 'default')" {
				error-message "Unknown routing instance";
			}
			configd:help "Routing Instance";
			configd:allowed "echo -n $VAR(/routing/routing-instance/@@)";
		}
	}

	container routing {
		description "Routing";
		configd:help "Routing";
		configd:begin "vrf-manager --add --all";
		configd:end "vrf-manager --del --all";
		configd:priority "100";
		list routing-instance {
			description "Routing Instance";
			configd:help "Routing Instance";
			key "instance-name";
			leaf instance-name {
				description "Routing Instance name";
				type routing-instance-name;
				must "((translate(current(),'ADEFLTU', 'adefltu') != 'default') and (translate(current(),'AL', 'al') != 'all'))" {
					error-message "Routing Instance names 'default' and 'all' are not allowed.";
				}
				configd:help "Routing Instance name";
			}
			leaf instance-type {
				description "Routing Instance type";
				type enumeration {
					enum "vrf" {
						description "VRF lite";
						configd:help "VRF lite";
					}
				}
				configd:help "Routing Instance type";
				default "vrf";
			}
			container protocols {
				description "Routing protocol parameters for Routing Instance";
				configd:help "Routing protocol parameters for Routing Instance";
			}
			container service {
				description "Services for Routing Instance";
				configd:help "Services for Routing Instance";
			}
			container system {
				description "System parameters for Routing Instance";
				configd:help "System parameters for Routing Instance";
				container login {
					description "Authentication services enabled in routing instance";
					configd:help "Authentication services enabled in routing instance";
					configd:end "/opt/vyatta/sbin/vyatta_update_login.pl --routing";
				}
			}
			container security {
				description "Security parameters for Routing Instance";
				configd:help "Security parameters for Routing Instance";
			}
			leaf description {
				description "Set description for this Routing-instance";
				configd:help "Set description for this Routing-instance";
				type string {
					length "1..80";
				}
			}
		}
	}
}
