module vyatta-interfaces-vif-v2 {
	namespace "urn:vyatta.com:mgmt:vyatta-interfaces-vif:2";
	prefix vyatta-interfaces-vif-v2;

	import vyatta-interfaces-v1 {
		prefix if;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2015-2016 by Brocade Communications Systems, Inc.
		 All rights reserved.

		 Vyatta system-level configuration utiliites, templates and scripts.";

	revision 2016-05-19 {
		description "Added status deprecated for host vif interface mtu.";
	}
	revision 2016-03-28 {
		description "Remove use of bash in action scripts";
	}
	revision 2015-08-14 {
		description "Initial revision of version 2.";
	}

	grouping vif-parameters {
		leaf description {
			type string;
			configd:help "Interface Description";
			configd:update "ip li set dev $VAR(../../@).$VAR(../@) alias '$VAR(@)'";
			configd:delete "vyatta-interfaces.pl --dev $VAR(../../@).$VAR(../@) --delete-description";
		}
		uses if:vif-parameters-base;
	}

	grouping vif-group-body {
		leaf vlan {
			type uint32 {
				range 1..4094;
			}
			configd:help "Virtual Local Area Network (VLAN) ID [REQUIRED]";
			configd:update "vyatta-interfaces.pl --dev $VAR(../../@) --update-vif $VAR(../@) --update-vlan";
			configd:delete "vyatta-interfaces.pl --dev $VAR(../../@) --update-vif $VAR(../@) --delete-vlan";
		}
		leaf inner-vlan {
			type uint32 {
				range 1..4094;
			}
			configd:help "Virtual Local Area Network (VLAN) ID";
			configd:update "vyatta-interfaces.pl --dev $VAR(../../@) --update-vif $VAR(../@) --update-ivlan";
			configd:delete "vyatta-interfaces.pl --dev $VAR(../../@) --update-vif $VAR(../@) --del-ivlan";
		}
		leaf disable-link-detect {
			type empty;
			configd:help "Ignore link state changes";
			configd:create "vyatta-link-detect $VAR(../@) off";
			configd:delete "vyatta-link-detect $VAR(../@) on";
		}
		uses vif-parameters;
	}
	grouping vif-group-base {
		configd:validate "vyatta-interfaces.pl --dev $VAR(@) --check-vifs";
		list vif {
			configd:priority "319";
			configd:help "Virtual Interface (VIF) ID";
			configd:create "vyatta-interfaces.pl --dev $VAR(../@) --create-vif $VAR(@)";
			configd:delete "vyatta-interfaces.pl --dev $VAR(../@) --delete-vif $VAR(@)";
			configd:validate "/opt/vyatta/share/tmplscripts/interfaces/vif/configd_validate1.cli";
			configd:end "vyatta-intf-end $VAR(../@).$VAR(@)";
			key "tagnode";
			unique "vlan inner-vlan";
			leaf tagnode {
				type uint32 {
					range 1..99999;
				}
				configd:help "Virtual Interface (VIF) ID";
			}
			uses vif-group-body;
			leaf mtu {
				status deprecated;
				type uint32 {
					range 68..9000;
				}
				configd:help "Maximum Transmission Unit (MTU)";
			}
			leaf-list address {
				type if:address-dhcp;
				ordered-by "user";
				configd:help "IP address";
				configd:create "vyatta-address add $VAR(../../@).$VAR(../@) $VAR(@)";
				configd:allowed "echo 'dhcp dhcpv6 <>'";
			}
		}
	}
	grouping vif-group {
		configd:validate "vyatta-interfaces.pl --dev $VAR(@) --check-vifs";
		list vif {
			configd:priority "319";
			configd:help "Virtual Interface (VIF) ID";
			configd:create "vyatta-interfaces.pl --dev $VAR(../@) --create-vif $VAR(@)";
			configd:delete "vyatta-interfaces.pl --dev $VAR(../@) --delete-vif $VAR(@)";
			configd:validate "/opt/vyatta/share/tmplscripts/interfaces/vif/configd_validate1.cli";
			configd:end "vyatta-intf-end $VAR(../@).$VAR(@)";
			key "tagnode";
			unique "vlan inner-vlan";
			leaf tagnode {
				type uint32 {
					range 1..99999;
				}
				configd:help "Virtual Interface (VIF) ID";
			}
			uses vif-group-body;
			leaf mtu {
				type uint32 {
					range 68..9000;
				}
				configd:priority "382";
				configd:help "Maximum Transmission Unit (MTU)";
				configd:update "vyatta-interfaces.pl --dev $VAR(../../@) --update-vif $VAR(../@) --set-mtu $VAR(@)";
				configd:delete "vyatta-interfaces.pl --dev $VAR(../../@) --update-vif $VAR(../@) --del-mtu 1500";
			}
			leaf-list address {
				type if:address-dhcp;
				ordered-by "user";
				configd:help "IP address";
				configd:create "vyatta-address add $VAR(../../@).$VAR(../@) $VAR(@)";
				configd:allowed "echo 'dhcp dhcpv6 <>'";
			}
		}
	}

	grouping vlan-proto-group {
		leaf vlan-protocol {
			type enumeration {
				enum 0x8100;
				enum 0x88A8;
				enum 0x9100;
				enum 0x9200;
				enum 0x9300;
			}
			configd:priority "381";
			configd:help "Vlan Tag Protocol Identifier (default: 0x8100)";
			default "0x8100";
			configd:update "vyatta-interfaces.pl --dev $VAR(../@) --update-vlan-proto $VAR(@)";
			configd:delete "vyatta-interfaces.pl --dev $VAR(../@) --update-vlan-proto 0x8100";
		}
	}
}
