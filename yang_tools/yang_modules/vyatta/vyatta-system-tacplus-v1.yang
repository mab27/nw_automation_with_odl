module vyatta-system-tacplus-v1 {
	namespace "urn:vyatta.com:mgmt:vyatta-system-tacplus:1";
	prefix vyatta-system-tacplus-v1;

	import vyatta-system-v1 {
		prefix system;
	}
	import vyatta-system-login-v1 {
		prefix system-login;
	}
	import vyatta-types-v1 {
		prefix types;
	}
	import configd-v1 {
		prefix configd;
	}
 
	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module for vyatta-system-tacplus-v1";

	revision 2016-02-19 {
		description "Create grouping for tacplus.";
	}
	revision 2015-08-18 {
		description "Use canned type for IPv4/IPv6 address.";
	}

	revision 2015-08-14 {
		description "Initial revision of version 1.";
	}

	augment /system:system {
		container tacplus-options {
			presence "true";
			configd:help "TACACS+ accounting";
			leaf command-accounting {
				type empty;
				configd:priority "410";
				configd:help "TACACS+ command accounting";
				configd:create "/opt/vyatta/share/tmplscripts/system/tacplus-options/command-accounting/configd_create.sh";
				configd:delete "/opt/vyatta/share/tmplscripts/system/tacplus-options/command-accounting/configd_delete.sh";
			}
		}
	}
	grouping tacplus-system-login-grouping {
		list tacplus-server {
			configd:help "TACACS+ server address";
			ordered-by "user";
			key "tagnode";
			leaf tagnode {
				type types:ip-address;
				configd:help "TACACS+ server address";
			}
			leaf source-address {
				type types:ip-address;
				configd:help "Source address to use for connecting to TACACS+ server";
			}
			leaf port {
				type uint16 {
					range 1..65535;
				}
				configd:help "TACACS+ server port";
				default "49";
			}
			leaf secret {
				type string {
					length 1..64;
					pattern "[!-~]+" {
						error-message "Secret must not contain space";
					}
				}
				configd:help "Secret for TACACS+ access [REQUIRED]";
				configd:secret "true";
				mandatory true;
			}
			leaf timeout {
				type uint32 {
					range 1..30;
				}
				configd:help "Timeout for TACACS+ session";
				default "3";
			}
		}
	}
	augment /system:system/system-login:login {
		uses tacplus-system-login-grouping;
	}
}
