module vyatta-protocols-ospfv3-v1 {
	namespace "urn:vyatta.com:mgmt:vyatta-protocols-ospfv3:1";
	prefix vyatta-protocols-ospfv3-v1;

	import vyatta-types-v1 {
		prefix types;
	}
	import vyatta-protocols-v1 {
		prefix protocols;
	}
	import configd-v1 {
		prefix configd;
	}
	import vyatta-policy-v1 {
		prefix policy;
	}
	import vyatta-policy-route-v1 {
		prefix policy-route;
	}
	import vyatta-interfaces-v1 {
		prefix if;
	}
	import vyatta-interfaces-bridge-v1 {
		prefix if-bridge;
	}
	import vyatta-interfaces-dataplane-v1 {
		prefix if-dataplane;
	}
	import vyatta-interfaces-l2tpeth-v1 {
		prefix if-l2tpeth;
	}
	import vyatta-interfaces-loopback-v1 {
		prefix if-loopback;
	}
	import vyatta-interfaces-openvpn-v1 {
		prefix if-openvpn;
	}
	import vyatta-interfaces-tunnel-v1 {
		prefix if-tunnel;
	}
	import vyatta-interfaces-vti-v1 {
		prefix if-vti;
	}
	import vyatta-interfaces-bonding-v1 {
		prefix if-bonding;
	}
	import vyatta-protocols-interface-validation-v1 {
		prefix if-validation;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module package for vyatta-protocols-ospfv3-v1";

	revision 2016-10-24 {
		description "add description to all yang nodes";
	}
	
	revision 2016-07-26 {
		description "Removed must statement for range under area node and
			added validation script,
			Remove passive-interface[-exclude] validation for
			erspan interfaces,
			Removed must statement for neighbor and added validate script,
			Created a new grouping for distribute-list under process
			configurations,
			Addition of validation script for range under ospfv3 process
			ipv4 address family unicast,
			Addition of instance-id validation for ospfv3 process
			under interface,
			Added validation for area,
			Renaming of passive-interface and passive-interface-exclude grouping,
			Improved validation for passive interface CLI,
			default-information originate script changes";
	}

	revision 2016-03-17 {
		description "Revision 2 - Enabling ospfv3 VRF CLI";
	}

	revision 2016-02-17 {
		description "New import of interface validation yang file and 
			Replaced validation scripts with yang grammar";
	}

	revision 2016-02-02 {
		description "Yang refactoring - yang grouping is done and new typedefs added";
	}

	revision 2015-08-06 {
		description "Initial revision of version 1";
	}

	typedef metric {
		type uint32 {
			range 0..16777214;
		}
	}

	typedef metric-type {
		type uint32 {
			range 1..2;
		}
	}

	typedef protocol {
		type enumeration {
			enum "bgp";
			enum "connected";
			enum "kernel";
			enum "rip";
			enum "static";
		}
	}

	typedef distance {
		type uint32 {
			range 1..254;
		}
	}

	typedef timer-val {
		type uint32 {
			range 1..65535;
		}
	}

	typedef spf-and-stability-interval {
		type uint32 {
			range 0..2147483647;
		}
	}

	typedef cost {
		type uint32 {
			range 1..65535;
		}
	}

	typedef tag {
		type uint32 {
			range min..2147483647;
		}
	}

	typedef abr-type {
		type enumeration {
			enum "cisco";
			enum "ibm";
			enum "standard";
		}
	}

	typedef nssa-tranlator-role {
		type enumeration {
			enum "candidate" {
				configd:help "Candidate for translator";
				description "Candidate for translator";
			}
			enum "always" {
				configd:help "Translate always";
				description "Translate always";
			}
		}
	}

	typedef network-type {
		type enumeration {
			enum "broadcast" {
				configd:help "Broadcast network type";
				description "Broadcast network type";
			}
			enum "non-broadcast" {
				configd:help "Non-broadcast network type";
				description "Non-broadcast network type";
			}
			enum "point-to-point" {
				configd:help "Point-to-point network type";
				description "Point-to-point network type";
			}
			enum "point-to-multipoint" {
				configd:help "Point-to-multipoint network type";
				description "Point-to-multipoint network type";
			}
		}
	}

	grouping ospfv3-ipv6-summary-address {
		list summary-address {
			configd:help "OSPFv3 Summary address";
			description "OSPFv3 Summary address";
			key "tagnode";
			leaf tagnode {
				type types:ipv6-prefix;
				configd:help "OSPFv3 Summary address";
				description "OSPFv3 Summary address";
				must "(../advertise) or (../not-advertise)" {
					error-message "Must specify one of advertise or not-advertise";
				}
			}
			container advertise {
				presence "true";
				configd:help "OSPFv3 summary address which should be advertised";
				description "OSPFv3 summary address which should be advertised";
				configd:create "/opt/vyatta/share/tmplscripts/protocols/ospfv3/summary-address/advertise/configd_create.sh";
				configd:delete "/opt/vyatta/share/tmplscripts/protocols/ospfv3/summary-address/advertise/configd_delete.sh";
				must "not(../not-advertise)" {
					error-message "Can't configure both advertise and not-advertise for summary-address";
				}
				leaf tag {
					type tag;
					configd:help "OSPFv3 tag identifier for summary address.";
					description "OSPFv3 tag identifier for summary address.";
					configd:create "/opt/vyatta/share/tmplscripts/protocols/ospfv3/summary-address/advertise/tag/configd_create.sh";
					configd:delete "/opt/vyatta/share/tmplscripts/protocols/ospfv3/summary-address/advertise/tag/configd_delete.sh";
				}
			}
			leaf not-advertise {
				type empty;
				configd:help "OSPFv3 summary address which shouldn't be advertised";
				description "OSPFv3 summary address which shouldn't be advertised";
				configd:create "/opt/vyatta/share/tmplscripts/protocols/ospfv3/summary-address/not-advertise/configd_create.sh";
				configd:delete "/opt/vyatta/share/tmplscripts/protocols/ospfv3/summary-address/not-advertise/configd_delete.sh";
			}
		}
	}

	grouping ospfv3-ipv4-summary-address {
		list summary-address {
			configd:help "OSPFv3 Summary address for address family";
			description "OSPFv3 Summary address for address family";
			key "tagnode";
			leaf tagnode {
				type types:ipv4-prefix;
				configd:help "OSPFv3 Summary address for address family";
				description "OSPFv3 Summary address for address family";
				must "(../advertise) or (../not-advertise)" {
					error-message "Must specify one of advertise or not-advertise";
				}
			}
			container advertise {
				presence "true";
				configd:help "OSPFv3 summary address which should be advertised";
				description "OSPFv3 summary address which should be advertised";
				configd:create "/opt/vyatta/share/tmplscripts/protocols/ospfv3/summary-address/advertise/configd_create.sh";
				configd:delete "/opt/vyatta/share/tmplscripts/protocols/ospfv3/summary-address/advertise/configd_delete.sh";
				must "not(../not-advertise)" {
					error-message "Can't configure both advertise and not-advertise for summary-address";
				}
				leaf tag {
					type tag;
					configd:help "OSPFv3 tag identifier for summary address.";
					description "OSPFv3 tag identifier for summary address.";
					configd:create "/opt/vyatta/share/tmplscripts/protocols/ospfv3/summary-address/advertise/tag/configd_create.sh";
					configd:delete "/opt/vyatta/share/tmplscripts/protocols/ospfv3/summary-address/advertise/tag/configd_delete.sh";
				}
			}
			leaf not-advertise {
				type empty;
				configd:help "OSPFv3 summary address which shouldn't be advertised";
				description "OSPFv3 summary address which shouldn't be advertised";
				configd:create "/opt/vyatta/share/tmplscripts/protocols/ospfv3/summary-address/not-advertise/configd_create.sh";
				configd:delete "/opt/vyatta/share/tmplscripts/protocols/ospfv3/summary-address/not-advertise/configd_delete.sh";
			}
		}

	}

	grouping parameters_redistribute {
		leaf metric-type {
			type metric-type;
			configd:help "Metric type for redistributed routes";
			description "Metric type for redistributed routes";
			default "2";
		}
		leaf route-map {
			type leafref {
				path "/policy:policy/policy-route:route/policy-route:route-map/policy-route:tagnode";
			}
			configd:help "Route map reference";
			description "Route map reference";
		}
		leaf metric {
			type metric;
			configd:help "Metric for redistributed routes";
			description "Metric for redistributed routes";
		}
		leaf tag {
			type uint32 {
				range 1..2147483647;
			}
			configd:help "Tag for redistributed routes";
			description "Tag for redistributed routes";
		}
	}
	grouping redistribute-protocols {
		container bgp {
			presence "true";
			configd:help "Redistribute bgp routes";
			description "Redistribute bgp routes";
			configd:end "/opt/vyatta/share/tmplscripts/protocols/ospfv3/redistribute/configd_end.sh";
			uses parameters_redistribute;
		}
		container kernel {
			presence "true";
			configd:help "Redistribute kernel routes";
			description "Redistribute kernel routes";
			configd:end "/opt/vyatta/share/tmplscripts/protocols/ospfv3/redistribute/configd_end.sh";
			uses parameters_redistribute;
		}
		container rip {
			presence "true";
			configd:help "Redistribute RIPNG routes";
			description "Redistribute RIPNG routes";
			configd:end "/opt/vyatta/share/tmplscripts/protocols/ospfv3/redistribute/configd_end.sh";
			uses parameters_redistribute;
		}
		container connected {
			presence "true";
			configd:help "Redistribute connected routes";
			description "Redistribute connected routes";
			configd:end "/opt/vyatta/share/tmplscripts/protocols/ospfv3/redistribute/configd_end.sh";
			uses parameters_redistribute;
		}
		container static {
			presence "true";
			configd:help "Redistribute static routes";
			description "Redistribute static routes";
			configd:end "/opt/vyatta/share/tmplscripts/protocols/ospfv3/redistribute/configd_end.sh";
			uses parameters_redistribute;
		}
	}
	grouping ospfv3-redistribute {
		container redistribute {
			presence "true";
			configd:help "Redistribute information from another routing protocol";
			description "Redistribute information from another routing protocol";
			uses redistribute-protocols;
		}
	}

	grouping ospfv3-ipv4-address-family-redistribute {
		container redistribute {
			presence "true";
			configd:help "Redistribute information from another routing protocol";
			description "Redistribute information from another routing protocol";
			uses redistribute-protocols;
			container ospf {
				presence "true";
				configd:help "Redistribute OSPF routes";
				description "Redistribute OSPF routes";
				configd:end "/opt/vyatta/share/tmplscripts/protocols/ospfv3/redistribute/configd_end.sh";
				uses parameters_redistribute;
			}
		}
	}
	/* configd:delete scripts for default-information originate has been removed and
	 * all the configurations will be handled as part of configd:end scripts.
	 */
	grouping ospfv3-default-information {
		container default-information {
			presence "true";
			configd:help "Control distribution of default information";
			description "Control distribution of default information";
			container originate {
				presence "true";
				configd:help "Distribute a default route";
				description "Distribute a default route";
				configd:end "/opt/vyatta/share/tmplscripts/protocols/ospfv3/default-information/originate/configd_end.sh";
				leaf metric-type {
					type metric-type;
					configd:help "OSPF metric type for default routes";
					description "OSPF metric type for default routes";
					default "2";
				}
				leaf always {
					type empty;
					configd:help "Always originate a default route";
					description "Always originate a default route";
				}
				leaf route-map {
					type leafref {
						path "/policy:policy/policy-route:route/policy-route:route-map/policy-route:tagnode";
					}
					configd:help "OSPF route-map to control default routes";
					description "OSPF route-map to control default routes";
				}
				leaf metric {
					type metric;
					configd:help "OSPF default metric";
					description "OSPF default metric";
				}
			}
		}
	}
	
	grouping area-default-cost {
		leaf default-cost {
			type uint32 {
				range 1..16777214;
			}
			configd:help "default-cost of area";
			description "default-cost of area";
			configd:create "/opt/vyatta/share/tmplscripts/protocols/ospfv3/area/default-cost/configd_create.sh";
			configd:delete "/opt/vyatta/share/tmplscripts/protocols/ospfv3/area/default-cost/configd_delete.sh";
		}
	}

	grouping spf-timers {
		container timers {
			presence "true";
			configd:help "OSPFv3 protocol configuration for timers";
			description "OSPFv3 protocol configuration for timers";
			container spf {
				presence "true";
				configd:help "OSPFv3 protocol configuration for SPF calculation";
				description "OSPFv3 protocol configuration for SPF calculation";
				container exp {
					presence "true";
					configd:help "OSPFv3 protocol configuration for exp backoff delays";
					description "OSPFv3 protocol configuration for exp backoff delays";
					configd:end "/opt/vyatta/share/tmplscripts/protocols/ospfv3/timers/spf/exp/configd_end.sh";
					must "(min <= max)" {
						error-message "Max delay must be greater or equal to Min delay value";
					}
					leaf max {
						type spf-and-stability-interval;
						configd:help "Maximum delay between receiving change to SPF calculation";
						description "Maximum delay between receiving change to SPF calculation";
						default "50000";
					}
					leaf min {
						type spf-and-stability-interval;
						configd:help "Minimum delay between receiving change to SPF calculation";
						description "Minimum delay between receiving change to SPF calculation";
						default "500";
					}
				}
			}
		}
	}

	grouping ospfv3-distribute-list {
		list distribute-list {
			configd:help "Access list to filter networks in routing updates";
			description "Access list to filter networks in routing updates";
			key "tagnode";
			leaf tagnode {
				type string {
					pattern '[!-~]{1,64}' {
						error-message "access-list name must be 64 characters or less";
					}
					pattern '[^-].*' {
						error-message "access-list name cannot start with \"-\"";
					}
					pattern '[^\|;&$<>]*' {
						error-message "access-list name cannot contain shell punctuation";
					}
				}
				configd:help "Access list to filter networks in routing updates";
				description "Access list to filter networks in routing updates";
			}
			leaf-list export {
				type protocol;
				ordered-by "user";
				configd:help "Filter for outgoing routing updates [REQUIRED]";
				description "Filter for outgoing routing updates [REQUIRED]";
				configd:create "/opt/vyatta/share/tmplscripts/protocols/ospfv3/distribute-list/export/configd_create.sh";
				configd:delete "/opt/vyatta/share/tmplscripts/protocols/ospfv3/distribute-list/export/configd_delete.sh";
			}
			leaf import {
				type empty;
				configd:help "Filter for incoming routing updates";
				description "Filter for incoming routing updates";
				configd:create "/opt/vyatta/share/tmplscripts/protocols/ospfv3/distribute-list/import/configd_create.sh";
				configd:delete "/opt/vyatta/share/tmplscripts/protocols/ospfv3/distribute-list/import/configd_delete.sh";
			}
		}
	}

	grouping ospfv3-distribute-list-process {
		list distribute-list {
			configd:help "Access list to filter networks in routing updates";
			description "Access list to filter networks in routing updates";
			key "tagnode";
			leaf tagnode {
				type string;
				configd:help "Access list to filter networks in routing updates";
				description "Access list to filter networks in routing updates";
			}
			leaf-list export {
				type protocol;
				ordered-by "user";
				configd:help "Filter for outgoing routing updates [REQUIRED]";
				description "Filter for outgoing routing updates [REQUIRED]";
				configd:create "/opt/vyatta/share/tmplscripts/protocols/ospfv3/distribute-list/export/configd_create.sh";
				configd:delete "/opt/vyatta/share/tmplscripts/protocols/ospfv3/distribute-list/export/configd_delete.sh";
			}
			leaf import {
				type empty;
				configd:help "Filter for incoming routing updates";
				description "Filter for incoming routing updates";
				configd:create "/opt/vyatta/share/tmplscripts/protocols/ospfv3/distribute-list/import/configd_create.sh";
				configd:delete "/opt/vyatta/share/tmplscripts/protocols/ospfv3/distribute-list/import/configd_delete.sh";
			}
		}
	}

	grouping ospfv3-passive-intf-default-routing-inst {
		uses if-validation:igp-passive-interface {
			refine "passive-interface" {
				configd:help "Suppress routing updates on an interface";
				description "Suppress routing updates on an interface";
				configd:priority "642";
				configd:create "/opt/vyatta/share/tmplscripts/protocols/ospfv3/passive-interface/configd_create.sh";
				configd:delete "/opt/vyatta/share/tmplscripts/protocols/ospfv3/passive-interface/configd_delete.sh";
				configd:validate "/opt/vyatta/share/tmplscripts/protocols/ospfv3/configd_validate.cli";
			}
		}
		uses if-validation:igp-passive-interface-exclude {
			refine "passive-interface-exclude" {
				configd:help "Excludes OSPFv3 routing update suppression on an interface";
				description "Excludes OSPFv3 routing update suppression on an interface";
				configd:priority "643";
				configd:create "/opt/vyatta/share/tmplscripts/protocols/ospfv3/passive-interface/exclude/configd_create.sh";
				configd:delete "/opt/vyatta/share/tmplscripts/protocols/ospfv3/passive-interface/exclude/configd_delete.sh";
				configd:validate "/opt/vyatta/share/tmplscripts/protocols/ospfv3/configd_validate.cli";
			}
		}
	}
	grouping ospfv3-generic-parameters {
		leaf default-metric {
			type uint32 {
				range 1..16777214;
			}
			configd:help "default-metric";
			description "default-metric";
			configd:create "/opt/vyatta/share/tmplscripts/protocols/ospfv3/default-metric/configd_create.sh";
			configd:delete "/opt/vyatta/share/tmplscripts/protocols/ospfv3/default-metric/configd_delete.sh";
		}
	}

	grouping ospfv3-generic-parameters-1 {
		container auto-cost {
			presence "true";
			configd:help "Set reference bandwidth";
			description "Set reference bandwidth";
			leaf reference-bandwidth {
				type uint32 {
					range 1..4294967;
				}
				configd:help "Reference bandwidth method to assign OSPF cost";
				description "Reference bandwidth method to assign OSPF cost";
				default "100";
				configd:update "/opt/vyatta/share/tmplscripts/protocols/ospfv3/auto-cost/reference-bandwidth/configd_update1.sh";
				configd:delete "/opt/vyatta/share/tmplscripts/protocols/ospfv3/auto-cost/reference-bandwidth/configd_delete1.sh";
			}
		}
		leaf router-id {
			type types:ipv4-address;
			configd:help "Router identifier";
			description "Router identifier";
			configd:update "/opt/vyatta/share/tmplscripts/protocols/ospfv3/router-id/configd_update.sh";
			configd:delete "/opt/vyatta/share/tmplscripts/protocols/ospfv3/router-id/configd_delete.sh";
			must "(current() != '0.0.0.0')" {
				error-message "Invalid Router-ID";
			}
		}
	}

	grouping ospfv3-distance {
		container distance {
			presence "true";
			configd:help "Administrative distance";
			description "Administrative distance";
			leaf global {
				type distance;
				configd:help "OSPF administrative distance";
				description "OSPF administrative distance";
				configd:update "/opt/vyatta/share/tmplscripts/protocols/ospfv3/distance/global/configd_update1.sh";
				configd:delete "/opt/vyatta/share/tmplscripts/protocols/ospfv3/distance/global/configd_delete1.sh";
			}
			container ospfv3 {
				presence "true";
				configd:help "OSPF administrative distance";
				description "OSPF administrative distance";
				leaf external {
					type distance;
					configd:help "Distance for external routes";
					description "Distance for external routes";
					configd:update "/opt/vyatta/share/tmplscripts/protocols/ospfv3/distance/ospfv3/external/configd_update1.sh";
					configd:delete "/opt/vyatta/share/tmplscripts/protocols/ospfv3/distance/ospfv3/external/configd_delete1.sh";
				}
				leaf inter-area {
					type distance;
					configd:help "Distance for inter-area routes";
					description "Distance for inter-area routes";
					configd:update "/opt/vyatta/share/tmplscripts/protocols/ospfv3/distance/ospfv3/inter-area/configd_update1.sh";
					configd:delete "/opt/vyatta/share/tmplscripts/protocols/ospfv3/distance/ospfv3/inter-area/configd_delete1.sh";
				}
				leaf intra-area {
					type distance;
					configd:help "Distance for intra-area routes";
					description "Distance for intra-area routes";
					configd:update "/opt/vyatta/share/tmplscripts/protocols/ospfv3/distance/ospfv3/intra-area/configd_update1.sh";
					configd:delete "/opt/vyatta/share/tmplscripts/protocols/ospfv3/distance/ospfv3/intra-area/configd_delete1.sh";
				}
			}
		}
	}

	grouping ospfv3-timers {
		leaf dead-interval {
			type timer-val;
			configd:help "Interval after which a neighbor is declared dead";
			description "Interval after which a neighbor is declared dead";
			configd:update "/opt/vyatta/share/tmplscripts/protocols/ospfv3/area/virtual-link/dead-interval/configd_update1.sh";
			configd:delete "/opt/vyatta/share/tmplscripts/protocols/ospfv3/area/virtual-link/dead-interval/configd_delete1.sh";
		}
		leaf hello-interval {
			type timer-val;
			configd:help "Interval between hello packets";
			description "Interval between hello packets";
			configd:update "/opt/vyatta/share/tmplscripts/protocols/ospfv3/area/virtual-link/hello-interval/configd_update1.sh";
			configd:delete "/opt/vyatta/share/tmplscripts/protocols/ospfv3/area/virtual-link/hello-interval/configd_delete1.sh";
		}
		leaf retransmit-interval {
			type timer-val;
			configd:help "Interval between retransmitting lost link state advertisements";
			description "Interval between retransmitting lost link state advertisements";
			configd:update "/opt/vyatta/share/tmplscripts/protocols/ospfv3/area/virtual-link/retransmit-interval/configd_update1.sh";
			configd:delete "/opt/vyatta/share/tmplscripts/protocols/ospfv3/area/virtual-link/retransmit-interval/configd_delete1.sh";
		}
		leaf transmit-delay {
			type timer-val;
			configd:help "Link state transmit delay";
			description "Link state transmit delay";
			configd:update "/opt/vyatta/share/tmplscripts/protocols/ospfv3/area/virtual-link/transmit-delay/configd_update1.sh";
			configd:delete "/opt/vyatta/share/tmplscripts/protocols/ospfv3/area/virtual-link/transmit-delay/configd_delete1.sh";
		}
	}

	grouping ospfv3-stub {
		container stub {
			presence "true";
			configd:help "Stub area";
			description "Stub area";
			configd:create "/opt/vyatta/share/tmplscripts/protocols/ospfv3/area/stub/configd_create.sh";
			configd:delete "/opt/vyatta/share/tmplscripts/protocols/ospfv3/area/stub/configd_delete.sh";
			uses area-default-cost;
			leaf no-summary {
				type empty;
				configd:help "Do not inject inter-area routes into stub";
				description "Do not inject inter-area routes into stub";
				configd:create "/opt/vyatta/share/tmplscripts/protocols/ospfv3/area/stub/no-summary/configd_create.sh";
				configd:delete "/opt/vyatta/share/tmplscripts/protocols/ospfv3/area/stub/no-summary/configd_delete.sh";
			}
		}
	}

	grouping ospfv3-virtual-link {
		list virtual-link {
			configd:help "OSPFv3 Virtual link";
			description "OSPFv3 Virtual link";
			configd:update "/opt/vyatta/share/tmplscripts/protocols/ospfv3/area/virtual-link/configd_update.sh";
			configd:delete "/opt/vyatta/share/tmplscripts/protocols/ospfv3/area/virtual-link/configd_delete.sh";
			key "tagnode";
			leaf tagnode {
				type types:ipv4-address;
				configd:help "OSPFv3 virtual neighbor ID";
				description "OSPFv3 virtual neighbor ID";
			}
			uses ospfv3-timers;
		}
	}

	grouping ospfv3-nssa-default-information {
		container default-information-originate {
			presence "true";
			configd:help "Originate Type 7 default into NSSA area";
			description "Originate Type 7 default into NSSA area";
			configd:update "/opt/vyatta/share/tmplscripts/protocols/ospfv3/area/nssa/default-information-originate/configd_update.sh";
			configd:delete "/opt/vyatta/share/tmplscripts/protocols/ospfv3/area/nssa/default-information-originate/configd_delete.sh";
			leaf metric-type {
				type metric-type;
				configd:help "OSPFv3 metric type for default routes";
				description "OSPFv3 metric type for default routes";
				configd:create "/opt/vyatta/share/tmplscripts/protocols/ospfv3/area/nssa/default-information-originate/metric-type/configd_create.sh";
				configd:delete "/opt/vyatta/share/tmplscripts/protocols/ospfv3/area/nssa/default-information-originate/metric-type/configd_delete.sh";
			}
			leaf metric {
				type metric;
				configd:help "OSPFv3 default metric";
				description "OSPFv3 default metric";
				configd:create "/opt/vyatta/share/tmplscripts/protocols/ospfv3/area/nssa/default-information-originate/metric/configd_create.sh";
				configd:delete "/opt/vyatta/share/tmplscripts/protocols/ospfv3/area/nssa/default-information-originate/metric/configd_delete.sh";
			}
		}
	}

	grouping ospfv3-nssa {
		container nssa {
			presence "true";
			configd:help "Configure OSPFv3 area as nssa";
			description "Configure OSPFv3 area as nssa";
			configd:end "/opt/vyatta/share/tmplscripts/protocols/ospfv3/area/nssa/configd_end.sh";
			uses area-default-cost;
			leaf stability-interval {
				type spf-and-stability-interval;
				configd:help "NSSA stability interval in seconds";
				description "NSSA stability interval in seconds";
				configd:create "/opt/vyatta/share/tmplscripts/protocols/ospfv3/area/nssa/stability-interval/configd_create.sh";
				configd:delete "/opt/vyatta/share/tmplscripts/protocols/ospfv3/area/nssa/stability-interval/configd_delete.sh";
			}
			leaf translator-role {
				type nssa-tranlator-role;
				configd:help "NSSA-ABR Translator role";
				description "NSSA-ABR Translator role";
				default "candidate";
				configd:create "/opt/vyatta/share/tmplscripts/protocols/ospfv3/area/nssa/translator-role/configd_create.sh";
				configd:delete "/opt/vyatta/share/tmplscripts/protocols/ospfv3/area/nssa/translator-role/configd_delete.sh";
			}
			leaf no-redistribution {
				type empty;
				configd:help "No redistribution into this NSSA area";
				description "No redistribution into this NSSA area";
				configd:end "/opt/vyatta/share/tmplscripts/protocols/ospfv3/area/nssa/no-redistribution/configd_end.sh";
			}
			uses ospfv3-nssa-default-information;
			leaf no-summary {
				type empty;
				configd:help "Do not send summary LSA into NSSA";
				description "Do not send summary LSA into NSSA";
				configd:end "/opt/vyatta/share/tmplscripts/protocols/ospfv3/area/nssa/no-summary/configd_end.sh";
			}
		}
	}

	grouping ospfv3-range {
		list range {
			configd:help "Area address range";
			description "Area address range";
			configd:end "/opt/vyatta/share/tmplscripts/protocols/ospfv3/area/range/configd_end.sh";
			key "tagnode";
			leaf tagnode {
				type types:ipv6-prefix {
					configd:normalize "normalize ipv6-prefix";
				}
				configd:help "Area address range";
				description "Area address range";
			}
			leaf advertise {
				type empty;
				configd:help "Advertise this range";
				description "Advertise this range";
			}
			leaf not-advertise {
				type empty;
				configd:help "Do not advertise this range";
				description "Do not advertise this range";
			}
		}
	}

	grouping ospfv3-area {
		list area {
			configd:help "OSPFv3 Area";
			description "OSPFv3 Area";
			key "tagnode";
			leaf tagnode {
				type union {
					type types:ipv4-address;
					type uint32;
				}
				must "not(current() = '0.0.0.0' or current() = 0) or not(../virtual-link | ../stub | ../nssa)" {
					error-message "Cannot configure area 0 (0.0.0.0) with virtual link, nor as nssa or stub area type";
				}
				must "(count(../nssa | ../stub | ../virtual-link) <= 1) or (count(../nssa | ../stub) = 0)" {
					error-message "Can only specify one of nssa, stub, or virtual-link";
				}
				configd:help "OSPFv3 Area";
				description "OSPFv3 Area";
			}
			uses ospfv3-stub;
			uses ospfv3-virtual-link;
			uses ospfv3-nssa;
			uses ospfv3-range;
		}
	}

	grouping ospfv3-area-ipv4-addr-family {
		list area {
			configd:help "OSPFv3 Area of address-family";
			description "OSPFv3 Area of address-family";
			key "tagnode";
			leaf tagnode {
				type union {
					type types:ipv4-address;
					type uint32;
				}
				configd:help "OSPFv3 Area of address-family";
				description "OSPFv3 Area of address-family";
			}
			list range {
				configd:help "Specify range (border routers only)";
				description "Specify range (border routers only)";
				configd:end "/opt/vyatta/share/tmplscripts/protocols/ospfv3/process/address-family/ipv4/unicast/area/range/configd_end.sh";
				key "tagnode";
				leaf tagnode {
					type types:ipv4-prefix {
						configd:normalize "normalize ipv4-prefix";
					}
					configd:help "Specify range (border routers only)";
					description "Specify range (border routers only)";
				}
				leaf advertise {
					type empty;
					configd:help "Advertise this range";
					description "Advertise this range";
				}
				leaf not-advertise {
					type empty;
					configd:help "Do not advertise this range";
					description "Do not advertise this range";
				}
			}
		}
	}

	grouping ospfv3-ipv4-address-family {
		container address-family {
			presence "true";
			configd:help "OSPFv3 address-family parameters";
			description "OSPFv3 address-family parameters";
			container ipv4 {
				presence "true";
				configd:help "IPv4 address family";
				description "IPv4 address family";
				container unicast {
					presence "true";
					configd:help "OSPFv3 IPv4-unicast address-family settings";
					description "OSPFv3 IPv4-unicast address-family settings";
					configd:create "/opt/vyatta/share/tmplscripts/protocols/ospfv3/process/address-family/ipv4/unicast/configd_create1.sh";
					configd:delete "/opt/vyatta/share/tmplscripts/protocols/ospfv3/process/address-family/ipv4/unicast/configd_delete1.sh";
					uses ospfv3-ipv4-address-family-redistribute;
					uses ospfv3-ipv4-summary-address;
					uses ospfv3-default-information;
					uses ospfv3-area-ipv4-addr-family;
				}
			}
		}
	}

	grouping ospfv3-abr-type {
		leaf abr-type {
			type abr-type;
			configd:help "Area Border Router type";
			description "Area Border Router type";
			configd:begin "/opt/vyatta/share/tmplscripts/protocols/ospfv3/abr-type/configd_begin.sh";
			configd:end "/opt/vyatta/share/tmplscripts/protocols/ospfv3/abr-type/configd_end.sh";
		}
	}

	grouping ospfv3-debug-parameters {
		container log {
			configd:help "OSPFv3 logging parameters";
			description "OSPFv3 logging parameters";
			leaf all {
				type empty;
				configd:help "Enable all OSPFv3 logs";
				description "Enable all OSPFv3 logs";
				configd:create "/opt/vyatta/share/tmplscripts/protocols/ospfv3/log/configd_create.sh";
				configd:delete "/opt/vyatta/share/tmplscripts/protocols/ospfv3/log/configd_delete.sh";
			}
			leaf retransmission {
				type empty;
				configd:help "Enable OSPFv3 retransmission logs";
				description "Enable OSPFv3 retransmission logs";
				configd:create "/opt/vyatta/share/tmplscripts/protocols/ospfv3/log/configd_create.sh";
				configd:delete "/opt/vyatta/share/tmplscripts/protocols/ospfv3/log/configd_delete.sh";
			}
			container rib {
				configd:help "OSPFv3 rib logs";
				description "OSPFv3 rib logs";
				leaf all {
					type empty;
					configd:help "Enable OSPFv3 rib all logs";
					description "Enable OSPFv3 rib all logs";
					configd:create "/opt/vyatta/share/tmplscripts/protocols/ospfv3/log/rib/configd_create.sh";
					configd:delete "/opt/vyatta/share/tmplscripts/protocols/ospfv3/log/rib/configd_delete.sh";
				}
				leaf interface {
					type empty;
					configd:help "Enable OSPFv3 rib interface logs";
					description "Enable OSPFv3 rib interface logs";
					configd:create "/opt/vyatta/share/tmplscripts/protocols/ospfv3/log/rib/configd_create.sh";
					configd:delete "/opt/vyatta/share/tmplscripts/protocols/ospfv3/log/rib/configd_delete.sh";
				}
				leaf redistribute {
					type empty;
					configd:help "Enable OSPFv3 rib redistribute logs";
					description "Enable OSPFv3 rib redistribute logs";
					configd:create "/opt/vyatta/share/tmplscripts/protocols/ospfv3/log/rib/configd_create.sh";
					configd:delete "/opt/vyatta/share/tmplscripts/protocols/ospfv3/log/rib/configd_delete.sh";
				}
			}
			container nsm {
				configd:help "OSPFv3 nsm logs";
				description "OSPFv3 nsm logs";
				leaf all {
					type empty;
					configd:help "Enable OSPFv3 nsm all logs";
					description "Enable OSPFv3 nsm all logs";
					configd:create "/opt/vyatta/share/tmplscripts/protocols/ospfv3/log/nsm/configd_create.sh";
					configd:delete "/opt/vyatta/share/tmplscripts/protocols/ospfv3/log/nsm/configd_delete.sh";
				}
				leaf interface {
					type empty;
					configd:help "Enable OSPFv3 nsm interface logs";
					description "Enable OSPFv3 nsm interface logs";
					configd:create "/opt/vyatta/share/tmplscripts/protocols/ospfv3/log/nsm/configd_create.sh";
					configd:delete "/opt/vyatta/share/tmplscripts/protocols/ospfv3/log/nsm/configd_delete.sh";
				}
				leaf redistribute {
					type empty;
					configd:help "Enable OSPFv3 nsm redistribute logs";
					description "Enable OSPFv3 nsm redistribute logs";
					configd:create "/opt/vyatta/share/tmplscripts/protocols/ospfv3/log/nsm/configd_create.sh";
					configd:delete "/opt/vyatta/share/tmplscripts/protocols/ospfv3/log/nsm/configd_delete.sh";
				}
			}
			container events {
				configd:help "OSPFv3 event logs";
				description "OSPFv3 event logs";
				leaf all {
					type empty;
					configd:help "Enable OSPFv3 events all logs";
					description "Enable OSPFv3 events all logs";
					configd:create "/opt/vyatta/share/tmplscripts/protocols/ospfv3/log/events/configd_create.sh";
					configd:delete "/opt/vyatta/share/tmplscripts/protocols/ospfv3/log/events/configd_delete.sh";
				}
				leaf abr {
					type empty;
					configd:help "Enable OSPFv3 events abr logs";
					description "Enable OSPFv3 events abr logs";
					configd:create "/opt/vyatta/share/tmplscripts/protocols/ospfv3/log/events/configd_create.sh";
					configd:delete "/opt/vyatta/share/tmplscripts/protocols/ospfv3/log/events/configd_delete.sh";
				}
				leaf asbr {
					type empty;
					configd:help "Enable OSPFv3 events asbr logs";
					description "Enable OSPFv3 events asbr logs";
					configd:create "/opt/vyatta/share/tmplscripts/protocols/ospfv3/log/events/configd_create.sh";
					configd:delete "/opt/vyatta/share/tmplscripts/protocols/ospfv3/log/events/configd_delete.sh";
				}
				leaf lsa {
					type empty;
					configd:help "Enable OSPFv3 events lsa logs";
					description "Enable OSPFv3 events lsa logs";
					configd:create "/opt/vyatta/share/tmplscripts/protocols/ospfv3/log/events/configd_create.sh";
					configd:delete "/opt/vyatta/share/tmplscripts/protocols/ospfv3/log/events/configd_delete.sh";
				}
				leaf nssa {
					type empty;
					configd:help "Enable OSPFv3 events nssa logs";
					description "Enable OSPFv3 events nssa logs";
					configd:create "/opt/vyatta/share/tmplscripts/protocols/ospfv3/log/events/configd_create.sh";
					configd:delete "/opt/vyatta/share/tmplscripts/protocols/ospfv3/log/events/configd_delete.sh";
				}
				leaf os {
					type empty;
					configd:help "Enable OSPFv3 events os logs";
					description "Enable OSPFv3 events os logs";
					configd:create "/opt/vyatta/share/tmplscripts/protocols/ospfv3/log/events/configd_create.sh";
					configd:delete "/opt/vyatta/share/tmplscripts/protocols/ospfv3/log/events/configd_delete.sh";
				}
				leaf router {
					type empty;
					configd:help "Enable OSPFv3 events router logs";
					description "Enable OSPFv3 events router logs";
					configd:create "/opt/vyatta/share/tmplscripts/protocols/ospfv3/log/events/configd_create.sh";
					configd:delete "/opt/vyatta/share/tmplscripts/protocols/ospfv3/log/events/configd_delete.sh";
				}
				leaf vlink {
					type empty;
					configd:help "Enable OSPFv3 events vlink logs";
					description "Enable OSPFv3 events vlink logs";
					configd:create "/opt/vyatta/share/tmplscripts/protocols/ospfv3/log/events/configd_create.sh";
					configd:delete "/opt/vyatta/share/tmplscripts/protocols/ospfv3/log/events/configd_delete.sh";
				}
			}
			container ifsm {
				configd:help "OSPFv3 ifsm logs";
				description "OSPFv3 ifsm logs";
				leaf all {
					type empty;
					configd:help "Enable OSPFv3 ifsm all logs";
					description "Enable OSPFv3 ifsm all logs";
					configd:create "/opt/vyatta/share/tmplscripts/protocols/ospfv3/log/ifsm/configd_create.sh";
					configd:delete "/opt/vyatta/share/tmplscripts/protocols/ospfv3/log/ifsm/configd_delete.sh";
				}
				leaf events {
					type empty;
					configd:help "Enable OSPFv3 ifsm events logs";
					description "Enable OSPFv3 ifsm events logs";
					configd:create "/opt/vyatta/share/tmplscripts/protocols/ospfv3/log/ifsm/configd_create.sh";
					configd:delete "/opt/vyatta/share/tmplscripts/protocols/ospfv3/log/ifsm/configd_delete.sh";
				}
				leaf status {
					type empty;
					configd:help "Enable OSPFv3 ifsm status logs";
					description "Enable OSPFv3 ifsm status logs";
					configd:create "/opt/vyatta/share/tmplscripts/protocols/ospfv3/log/ifsm/configd_create.sh";
					configd:delete "/opt/vyatta/share/tmplscripts/protocols/ospfv3/log/ifsm/configd_delete.sh";
				}
				leaf timers {
					type empty;
					configd:help "Enable OSPFv3 ifsm timers logs";
					description "Enable OSPFv3 ifsm timers logs";
					configd:create "/opt/vyatta/share/tmplscripts/protocols/ospfv3/log/ifsm/configd_create.sh";
					configd:delete "/opt/vyatta/share/tmplscripts/protocols/ospfv3/log/ifsm/configd_delete.sh";
				}
			}
			container lsa {
				configd:help "OSPFv3 lsa logs";
				description "OSPFv3 lsa logs";
				leaf all {
					type empty;
					configd:help "Enable OSPFv3 lsa all logs";
					description "Enable OSPFv3 lsa all logs";
					configd:create "/opt/vyatta/share/tmplscripts/protocols/ospfv3/log/lsa/configd_create.sh";
					configd:delete "/opt/vyatta/share/tmplscripts/protocols/ospfv3/log/lsa/configd_delete.sh";
				}
				leaf flooding {
					type empty;
					configd:help "Enable OSPFv3 lsa flooding logs";
					description "Enable OSPFv3 lsa flooding logs";
					configd:create "/opt/vyatta/share/tmplscripts/protocols/ospfv3/log/lsa/configd_create.sh";
					configd:delete "/opt/vyatta/share/tmplscripts/protocols/ospfv3/log/lsa/configd_delete.sh";
				}
				leaf generate {
					type empty;
					configd:help "Enable OSPFv3 lsa generate logs";
					description "Enable OSPFv3 lsa generate logs";
					configd:create "/opt/vyatta/share/tmplscripts/protocols/ospfv3/log/lsa/configd_create.sh";
					configd:delete "/opt/vyatta/share/tmplscripts/protocols/ospfv3/log/lsa/configd_delete.sh";
				}
				leaf install {
					type empty;
					configd:help "Enable OSPFv3 lsa install logs";
					description "Enable OSPFv3 lsa install logs";
					configd:create "/opt/vyatta/share/tmplscripts/protocols/ospfv3/log/lsa/configd_create.sh";
					configd:delete "/opt/vyatta/share/tmplscripts/protocols/ospfv3/log/lsa/configd_delete.sh";
				}
				leaf maxage {
					type empty;
					configd:help "Enable OSPFv3 lsa maxage logs";
					description "Enable OSPFv3 lsa maxage logs";
					configd:create "/opt/vyatta/share/tmplscripts/protocols/ospfv3/log/lsa/configd_create.sh";
					configd:delete "/opt/vyatta/share/tmplscripts/protocols/ospfv3/log/lsa/configd_delete.sh";
				}
				leaf refresh {
					type empty;
					configd:help "Enable OSPFv3 lsa refresh logs";
					description "Enable OSPFv3 lsa refresh logs";
					configd:create "/opt/vyatta/share/tmplscripts/protocols/ospfv3/log/lsa/configd_create.sh";
					configd:delete "/opt/vyatta/share/tmplscripts/protocols/ospfv3/log/lsa/configd_delete.sh";
				}
			}
			container nfsm {
				configd:help "OSPFv3 nfsm logs";
				description "OSPFv3 nfsm logs";
				leaf all {
					type empty;
					configd:help "Enable OSPFv3 nfsm all logs";
					description "Enable OSPFv3 nfsm all logs";
					configd:create "/opt/vyatta/share/tmplscripts/protocols/ospfv3/log/nfsm/configd_create.sh";
					configd:delete "/opt/vyatta/share/tmplscripts/protocols/ospfv3/log/nfsm/configd_delete.sh";
				}
				leaf events {
					type empty;
					configd:help "Enable OSPFv3 nfsm events logs";
					description "Enable OSPFv3 nfsm events logs";
					configd:create "/opt/vyatta/share/tmplscripts/protocols/ospfv3/log/nfsm/configd_create.sh";
					configd:delete "/opt/vyatta/share/tmplscripts/protocols/ospfv3/log/nfsm/configd_delete.sh";
				}
				leaf status {
					type empty;
					configd:help "Enable OSPFv3 nfsm status logs";
					description "Enable OSPFv3 nfsm status logs";
					configd:create "/opt/vyatta/share/tmplscripts/protocols/ospfv3/log/nfsm/configd_create.sh";
					configd:delete "/opt/vyatta/share/tmplscripts/protocols/ospfv3/log/nfsm/configd_delete.sh";
				}
				leaf timers {
					type empty;
					configd:help "Enable OSPFv3 nfsm timers logs";
					description "Enable OSPFv3 nfsm timers logs";
					configd:create "/opt/vyatta/share/tmplscripts/protocols/ospfv3/log/nfsm/configd_create.sh";
					configd:delete "/opt/vyatta/share/tmplscripts/protocols/ospfv3/log/nfsm/configd_delete.sh";
				}
			}
			container route {
				configd:help "OSPFv3 route logs";
				description "OSPFv3 route logs";
				leaf all {
					type empty;
					configd:help "Enable OSPFv3 route all logs";
					description "Enable OSPFv3 route all logs";
					configd:create "/opt/vyatta/share/tmplscripts/protocols/ospfv3/log/route/configd_create.sh";
					configd:delete "/opt/vyatta/share/tmplscripts/protocols/ospfv3/log/route/configd_delete.sh";
				}
				leaf ase {
					type empty;
					configd:help "Enable OSPFv3 route ase logs";
					description "Enable OSPFv3 route ase logs";
					configd:create "/opt/vyatta/share/tmplscripts/protocols/ospfv3/log/route/configd_create.sh";
					configd:delete "/opt/vyatta/share/tmplscripts/protocols/ospfv3/log/route/configd_delete.sh";
				}
				leaf ia {
					type empty;
					configd:help "Enable OSPFv3 route ia logs";
					description "Enable OSPFv3 route ia logs";
					configd:create "/opt/vyatta/share/tmplscripts/protocols/ospfv3/log/route/configd_create.sh";
					configd:delete "/opt/vyatta/share/tmplscripts/protocols/ospfv3/log/route/configd_delete.sh";
				}
				leaf install {
					type empty;
					configd:help "Enable OSPFv3 route install logs";
					description "Enable OSPFv3 route install logs";
					configd:create "/opt/vyatta/share/tmplscripts/protocols/ospfv3/log/route/configd_create.sh";
					configd:delete "/opt/vyatta/share/tmplscripts/protocols/ospfv3/log/route/configd_delete.sh";
				}
				leaf spf {
					type empty;
					configd:help "Enable OSPFv3 route spf logs";
					description "Enable OSPFv3 route spf logs";
					configd:create "/opt/vyatta/share/tmplscripts/protocols/ospfv3/log/route/configd_create.sh";
					configd:delete "/opt/vyatta/share/tmplscripts/protocols/ospfv3/log/route/configd_delete.sh";
				}
			}
			container packet {
				configd:help "OSPFv3 packet logs";
				description "OSPFv3 packet logs";
				leaf all {
					type empty;
					configd:help "Enable OSPFv3 packet all logs";
					description "Enable OSPFv3 packet all logs";
					configd:create "/opt/vyatta/share/tmplscripts/protocols/ospfv3/log/packet/configd_create.sh";
					configd:delete "/opt/vyatta/share/tmplscripts/protocols/ospfv3/log/packet/configd_delete.sh";
				}
				leaf dd {
					type empty;
					configd:help "Enable OSPFv3 packet dd logs";
					description "Enable OSPFv3 packet dd logs";
					configd:create "/opt/vyatta/share/tmplscripts/protocols/ospfv3/log/packet/configd_create.sh";
					configd:delete "/opt/vyatta/share/tmplscripts/protocols/ospfv3/log/packet/configd_delete.sh";
				}
				leaf detail {
					type empty;
					configd:help "Enable OSPFv3 packet detail logs";
					description "Enable OSPFv3 packet detail logs";
					configd:create "/opt/vyatta/share/tmplscripts/protocols/ospfv3/log/packet/configd_create.sh";
					configd:delete "/opt/vyatta/share/tmplscripts/protocols/ospfv3/log/packet/configd_delete.sh";
				}
				leaf hello {
					type empty;
					configd:help "Enable OSPFv3 packet hello logs";
					description "Enable OSPFv3 packet hello logs";
					configd:create "/opt/vyatta/share/tmplscripts/protocols/ospfv3/log/packet/configd_create.sh";
					configd:delete "/opt/vyatta/share/tmplscripts/protocols/ospfv3/log/packet/configd_delete.sh";
				}
				leaf ls-ack {
					type empty;
					configd:help "Enable OSPFv3 packet ls-ack logs";
					description "Enable OSPFv3 packet ls-ack logs";
					configd:create "/opt/vyatta/share/tmplscripts/protocols/ospfv3/log/packet/configd_create.sh";
					configd:delete "/opt/vyatta/share/tmplscripts/protocols/ospfv3/log/packet/configd_delete.sh";
				}
				leaf ls-request {
					type empty;
					configd:help "Enable OSPFv3 packet ls-request logs";
					description "Enable OSPFv3 packet ls-request logs";
					configd:create "/opt/vyatta/share/tmplscripts/protocols/ospfv3/log/packet/configd_create.sh";
					configd:delete "/opt/vyatta/share/tmplscripts/protocols/ospfv3/log/packet/configd_delete.sh";
				}
				leaf ls-update {
					type empty;
					configd:help "Enable OSPFv3 packet ls-update logs";
					description "Enable OSPFv3 packet ls-update logs";
					configd:create "/opt/vyatta/share/tmplscripts/protocols/ospfv3/log/packet/configd_create.sh";
					configd:delete "/opt/vyatta/share/tmplscripts/protocols/ospfv3/log/packet/configd_delete.sh";
				}
				leaf send {
					type empty;
					configd:help "Enable OSPFv3 packet send logs";
					description "Enable OSPFv3 packet send logs";
					configd:create "/opt/vyatta/share/tmplscripts/protocols/ospfv3/log/packet/configd_create.sh";
					configd:delete "/opt/vyatta/share/tmplscripts/protocols/ospfv3/log/packet/configd_delete.sh";
				}
				leaf recv {
					type empty;
					configd:help "Enable OSPFv3 packet recv logs";
					description "Enable OSPFv3 packet recv logs";
					configd:create "/opt/vyatta/share/tmplscripts/protocols/ospfv3/log/packet/configd_create.sh";
					configd:delete "/opt/vyatta/share/tmplscripts/protocols/ospfv3/log/packet/configd_delete.sh";
				}
			}
			leaf bfd {
				type empty;
					configd:help "Enable OSPFv3 BFD logs";
					description "Enable OSPFv3 BFD logs";
					configd:create "/opt/vyatta/share/tmplscripts/protocols/ospfv3/log/configd_create.sh";
					configd:delete "/opt/vyatta/share/tmplscripts/protocols/ospfv3/log/configd_delete.sh";
			}
		}
	}

	augment /protocols:protocols {
		container ospfv3 {
			presence "true";
			configd:priority "640";
			configd:help "Open Shortest Path First version 3 protocol (OSPFv3) parameters";
			description "Open Shortest Path First version 3 protocol (OSPFv3) parameters";
			configd:create "/opt/vyatta/share/tmplscripts/protocols/ospfv3/configd_create.sh";
			configd:delete "/opt/vyatta/share/tmplscripts/protocols/ospfv3/configd_delete.sh";
			uses spf-timers;
			uses ospfv3-distribute-list;
			uses ospfv3-passive-intf-default-routing-inst;
			uses ospfv3-generic-parameters;
			list process {
				configd:priority "641";
				configd:help "OSPFv3 process name";
				description "OSPFv3 process name";
				configd:update "/opt/vyatta/share/tmplscripts/protocols/ospfv3/process/configd_update.sh";
				configd:delete "/opt/vyatta/share/tmplscripts/protocols/ospfv3/process/configd_delete.sh";
				key "tagnode";
				leaf tagnode {
					type string {
						pattern '[0-9A-Za-z][-_0-9A-Za-z]*' {
							error-message "name must be alphanumeric (hyphen/underscore may be used inside)";
						}
					}
					configd:help "OSPFv3 process name";
					description "OSPFv3 process name";
				}
				uses spf-timers;
				uses ospfv3-distribute-list-process;
				uses ospfv3-passive-intf-default-routing-inst;
				uses ospfv3-generic-parameters;
				uses ospfv3-redistribute;
				uses ospfv3-distance;
				uses ospfv3-abr-type;
				uses ospfv3-ipv6-summary-address;
				uses ospfv3-default-information;
				uses ospfv3-ipv4-address-family {
					refine address-family/ipv4/unicast/area/range/advertise {
						configd:validate "/opt/vyatta/share/tmplscripts/protocols/ospfv3/range/configd_validate.sh";
					}
				}
				uses ospfv3-area {
					refine area/range/advertise {
						configd:validate "/opt/vyatta/share/tmplscripts/protocols/ospfv3/range/configd_validate.sh";
					}
				}
				uses ospfv3-generic-parameters-1;
				uses ospfv3-debug-parameters;
			}
			uses ospfv3-redistribute;
			uses ospfv3-distance;
			uses ospfv3-ipv6-summary-address;
			uses ospfv3-default-information;
			uses ospfv3-area {
				refine area/range/advertise {
					configd:validate "/opt/vyatta/share/tmplscripts/protocols/ospfv3/range/configd_validate.sh";
				}
			}
			uses ospfv3-generic-parameters-1;
			uses ospfv3-debug-parameters;
		}
	}

	grouping ospfv3-itf-parameters {
		leaf link-lsa-suppression {
			type string {
				pattern 'enable' {
					error-message "Only valid setting is 'enable'";
				}
				configd:pattern-help "enable";
			}
			configd:help "Enable link-lsa-suppression for this instance-id";
			description "Enable link-lsa-suppression for this instance-id";
			configd:create "/opt/vyatta/share/tmplscripts/interfaces/all/ipv6/ospfv3/link-lsa-suppression/configd_create.sh";
			configd:delete "/opt/vyatta/share/tmplscripts/interfaces/all/ipv6/ospfv3/link-lsa-suppression/configd_delete.sh";
		}
		leaf priority {
			type uint32 {
				range 0..255;
			}
			configd:help "Router priority (default 1)";
			description "Router priority (default 1)";
			configd:update "/opt/vyatta/share/tmplscripts/interfaces/all/ipv6/ospfv3/priority/configd_update.sh";
			configd:delete "/opt/vyatta/share/tmplscripts/interfaces/all/ipv6/ospfv3/priority/configd_delete.sh";
		}
	}
	/* The reference in the below must condition restricts the usage of ospfv3-itf-neighbor grouping
	 * in other places, the must statement can be moved out of the grouping and refine statement can
	 * be used if required.
	 */
	grouping ospfv3-itf-neighbor {
		list neighbor {
			configd:help "Configure ipv6 address for neighbor parameters";
			description "Configure ipv6 address for neighbor parameters";
			configd:priority "950";
			configd:update "/opt/vyatta/share/tmplscripts/interfaces/all/ipv6/ospfv3/neighbor/configd_update.sh";
			configd:delete "/opt/vyatta/share/tmplscripts/interfaces/all/ipv6/ospfv3/neighbor/configd_delete.sh";
			key "tagnode";
			leaf tagnode {
				type types:ipv6-address;
				configd:help "Configure ipv6 address for neighbor parameters";
				description "Configure ipv6 address for neighbor parameters";
				configd:validate "/opt/vyatta/share/tmplscripts/interfaces/all/ipv6/ospfv3/neighbor/configd_validate.sh";
			}
		}
	}

	grouping ospfv3-itf-timers {
		leaf dead-interval {
			type timer-val;
			configd:help "Interval after which neighbor is declared dead (default 40)";
			description "Interval after which neighbor is declared dead (default 40)";
			configd:update "/opt/vyatta/share/tmplscripts/interfaces/all/ipv6/ospfv3/dead-interval/configd_update.sh";
			configd:delete "/opt/vyatta/share/tmplscripts/interfaces/all/ipv6/ospfv3/dead-interval/configd_delete.sh";
		}
		leaf hello-interval {
			type timer-val;
			configd:help "Interval between hello packets (default 10)";
			description "Interval between hello packets (default 10)";
			configd:update "/opt/vyatta/share/tmplscripts/interfaces/all/ipv6/ospfv3/hello-interval/configd_update.sh";
			configd:delete "/opt/vyatta/share/tmplscripts/interfaces/all/ipv6/ospfv3/hello-interval/configd_delete.sh";
		}
		leaf retransmit-interval {
			type uint32 {
				range 3..65535;
			}
			configd:help "Interval between retransmitting lost link state advertisements (default 5)";
			description "Interval between retransmitting lost link state advertisements (default 5)";
			configd:update "/opt/vyatta/share/tmplscripts/interfaces/all/ipv6/ospfv3/retransmit-interval/configd_update.sh";
			configd:delete "/opt/vyatta/share/tmplscripts/interfaces/all/ipv6/ospfv3/retransmit-interval/configd_delete.sh";
		}
	}

	grouping ospfv3-itf-parameters-1 {
		leaf area {
			type union {
				type types:ipv4-address;
				type uint32;
			}
			configd:help "OSPFv3 area";
			description "OSPFv3 area";
			configd:update "/opt/vyatta/share/tmplscripts/interfaces/all/ipv6/ospfv3/area/configd_update.sh";
			configd:delete "/opt/vyatta/share/tmplscripts/interfaces/all/ipv6/ospfv3/area/configd_delete.sh";
		}
		leaf cost {
			type cost;
			configd:help "Interface cost";
			description "Interface cost";
			configd:update "/opt/vyatta/share/tmplscripts/interfaces/all/ipv6/ospfv3/cost/configd_update.sh";
			configd:delete "/opt/vyatta/share/tmplscripts/interfaces/all/ipv6/ospfv3/cost/configd_delete.sh";
		}
		list network {
			max-elements "1";
			configd:help "Network type";
			description "Network type";
			configd:priority "949";
			configd:update "/opt/vyatta/share/tmplscripts/interfaces/all/ipv6/ospfv3/network/configd_update.sh";
			configd:delete "/opt/vyatta/share/tmplscripts/interfaces/all/ipv6/ospfv3/network/configd_delete.sh";
			key "tagnode";
			leaf tagnode {
				type network-type;
				configd:help "Network type";
				description "Network type";
			}
		}
		leaf transmit-delay {
			type timer-val;
			configd:help "Link state transmit delay (default 1)";
			description "Link state transmit delay (default 1)";
			configd:update "/opt/vyatta/share/tmplscripts/interfaces/all/ipv6/ospfv3/transmit-delay/configd_update.sh";
			configd:delete "/opt/vyatta/share/tmplscripts/interfaces/all/ipv6/ospfv3/transmit-delay/configd_delete.sh";
		}
	}

	grouping ospfv3-itf-mtu-ignore {
		leaf mtu-ignore {
			type empty;
			configd:help "Disable Maximum Transmission Unit mismatch detection";
			description "Disable Maximum Transmission Unit mismatch detection";
			configd:create "/opt/vyatta/share/tmplscripts/interfaces/all/ipv6/ospfv3/mtu-ignore/configd_create.sh";
			configd:delete "/opt/vyatta/share/tmplscripts/interfaces/all/ipv6/ospfv3/mtu-ignore/configd_delete.sh";
		}
	}

	grouping itf-ipv6-ospfv3 {
		container ospfv3 {
			configd:priority "948";
			configd:help "Set OSPFv3 instance parameters";
			description "Set OSPFv3 instance parameters";
			uses ospfv3-itf-parameters;
			list process {
				configd:help "IPv6 Open Shortest Path First (OSPFv3) Process ID";
				description "IPv6 Open Shortest Path First (OSPFv3) Process ID";
				configd:allowed "/opt/vyatta/share/tmplscripts/interfaces/all/ipv6/ospfv3/process/configd_allowed.sh";
				key "tagnode";
				leaf tagnode {
					type string;
					configd:help "IPv6 Open Shortest Path First (OSPFv3) Process ID";
					description "IPv6 Open Shortest Path First (OSPFv3) Process ID";
					configd:allowed "/opt/vyatta/share/tmplscripts/interfaces/all/ipv6/ospfv3/process/configd_allowed.sh";
				}
				list instance-id {
					max-elements "1";
					configd:help "Instance-id";
					description "Instance-id";
					key "tagnode";
					leaf tagnode {
						type uint32 {
							range 0..255;
						}
						must "count(../../../process/instance-id[tagnode = current()]) <= 1" {
							error-message "Cannot configure same instance ID across multiple processes";
						}
						configd:help "Instance-id";
						description "Instance-id";
						configd:validate "/opt/vyatta/share/tmplscripts/interfaces/all/ipv6/ospfv3/process/configd_validate.sh";
					}
					uses ospfv3-itf-parameters;
					uses ospfv3-itf-neighbor;
					uses ospfv3-itf-timers;
					uses ospfv3-itf-parameters-1 {
						refine network {
							must "not(../../../../../if-loopback:tagnode) or (current() = 'point-to-point')" {
								error-message "Only point-to-point network is valid for loopback interfaces";
							}
						}
					}
					uses ospfv3-itf-mtu-ignore;
				}
			}
			uses ospfv3-itf-neighbor;
			uses ospfv3-itf-mtu-ignore;
			uses ospfv3-itf-timers;
			uses ospfv3-itf-parameters-1 {
				refine network {
					must "not(../../../if-loopback:tagnode) or (current() = 'point-to-point')" {
						error-message "Only point-to-point network is valid for loopback interfaces";
					}
				}
			}
		}
	}

	augment /if:interfaces/if-bridge:bridge/if-bridge:ipv6 {
		uses itf-ipv6-ospfv3;
	}
	augment /if:interfaces/if-dataplane:dataplane/if-dataplane:ipv6 {
		uses itf-ipv6-ospfv3;
	}
	augment /if:interfaces/if-dataplane:dataplane/if-dataplane:vif/if-dataplane:ipv6 {
		uses itf-ipv6-ospfv3;
	}
	augment /if:interfaces/if-l2tpeth:l2tpeth/if-l2tpeth:ipv6 {
		uses itf-ipv6-ospfv3;
	}
	augment /if:interfaces/if-l2tpeth:l2tpeth/if-l2tpeth:vif/if-l2tpeth:ipv6 {
		uses itf-ipv6-ospfv3;
	}
	augment /if:interfaces/if-loopback:loopback/if-loopback:ipv6 {
		uses itf-ipv6-ospfv3;
	}
	augment /if:interfaces/if-openvpn:openvpn/if-openvpn:ipv6 {
		uses itf-ipv6-ospfv3;
	}
	augment /if:interfaces/if-tunnel:tunnel/if-tunnel:ipv6 {
		uses itf-ipv6-ospfv3;
	}
	augment /if:interfaces/if-vti:vti/if-vti:ipv6 {
		uses itf-ipv6-ospfv3;
	}
	augment /if:interfaces/if-bonding:bonding/if-bonding:ipv6 {
		uses itf-ipv6-ospfv3;
	}
	augment /if:interfaces/if-bonding:bonding/if-bonding:vif/if-bonding:ipv6 {
		uses itf-ipv6-ospfv3;
	}
}
