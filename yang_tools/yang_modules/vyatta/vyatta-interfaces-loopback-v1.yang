module vyatta-interfaces-loopback-v1 {
	namespace "urn:vyatta.com:mgmt:vyatta-interfaces-loopback:1";
	prefix vyatta-interfaces-loopback-v1;

	import vyatta-interfaces-v1 {
		prefix if;
	}

	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 Loopback interface configuration";

	revision 2015-08-14 {
		description "Initial revision of version 1.";
	}

	augment /if:interfaces {
		list loopback {
			configd:priority "300";
			configd:help "Loopback interface name";
			configd:allowed "/opt/vyatta/share/tmplscripts/interfaces/loopback/configd_allowed.sh";
			configd:validate "interface-address-check $VAR(@) $VAR(./address/@@)";
			configd:create "/opt/vyatta/share/tmplscripts/interfaces/loopback/configd_create.sh";
			configd:delete "/opt/vyatta/share/tmplscripts/interfaces/loopback/configd_delete.sh";
			configd:end "/opt/vyatta/sbin/vyatta-unnumbered-update-donor.pl --dev=$VAR(@)";
			key "tagnode";
			leaf tagnode {
				type string {
					pattern "lo(|[1-9]([0-9]){0,4})" {
						error-message "name must be lo or loN, N in [1-99999]";
					}
					configd:pattern-help "<lo|lo[1-99999]>";
					configd:syntax "/opt/vyatta/share/tmplscripts/interfaces/loopback/configd_syntax1.cli";
				}
				configd:help "Loopback interface name";
				configd:allowed "/opt/vyatta/share/tmplscripts/interfaces/loopback/configd_allowed.sh";
			}
			leaf description {
				type string {
					pattern ".{1,256}" {
						error-message "interface description is too long (limit 256 characters)";
					}
				}
				configd:help "Description";
				configd:update "/opt/vyatta/share/tmplscripts/interfaces/loopback/description/configd_update.sh";
				configd:delete "/opt/vyatta/share/tmplscripts/interfaces/loopback/description/configd_delete.sh";
			}
			leaf-list address {
				type if:address;
				ordered-by "user";
				configd:help "IP address";
				configd:create "/opt/vyatta/share/tmplscripts/interfaces/loopback/address/configd_create.sh";
				configd:validate "/opt/vyatta/share/tmplscripts/interfaces/loopback/address/configd_validate.cli";
			}
			container ip {
				configd:help "IPv4 parameters";
			}
			container ipv6 {
				presence "true";
				configd:help "IPv6 parameters";
			}
		}
	}
}
