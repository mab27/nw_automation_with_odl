module vyatta-service-dns-routing-instance-v1 {
	namespace "urn:vyatta.com:mgmt:vyatta-service-dns-routing-instance:1";
	prefix vyatta-service-dns-routing-instance-v1;

	import configd-v1 {
		prefix configd;
	}
	import vyatta-system-network-routing-instance-v1 {
		prefix rt-sys-net;
	}
	import vyatta-routing-v1 {
		prefix rt-instance;
	}
	import vyatta-service-dns-v1 {
		prefix service-dns;
	}

	organization "Brocade Communications Systems, Inc.";
	contact
		"Brocade Communications Systems, Inc.
		Postal: 130 Holger Way
		San Jose, CA 95134
		E-mail: support@Brocade.com
		Web: www.brocade.com";

	description
		"Copyright (c) 2016 by Brocade Communications Systems, Inc.
		 All rights reserved.

		 The YANG module for vyatta-service-dns-routing-instance-v1";

	revision 2016-04-18 {
		description "Add dns to routing instance.";
	}

	augment /rt-instance:routing/rt-instance:routing-instance/rt-instance:service {
	container dns {
			presence "Enable service DNS for routing instance";
			description "Dns service in routing-instance";
			configd:help "Domain Name Server (DNS) parameters";
			uses service-dns:dns-service-forwarding {
				refine forwarding/system {
					must "/rt-instance:routing/rt-instance:routing-instance/rt-instance:system/rt-sys-net:name-server" {
					error-message
						"No name-servers set under 'routing-instance system name-server";
					}
				}
			}
			uses service-dns:dns-service-dynamic;
		}
	}
}
