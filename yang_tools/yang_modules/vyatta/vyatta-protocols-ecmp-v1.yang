module vyatta-protocols-ecmp-v1 {
	namespace "urn:vyatta.com:mgmt:vyatta-protocols-ecmp:1";
	prefix vyatta-protocols-ecmp-v1;

	import vyatta-protocols-v1 {
		prefix protocols;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module package for vyatta-protocols-ecmp-v1";

	revision 2016-06-01 {
		description "Grouping maximum-paths and disable leaf node";
	}

	revision 2014-08-06 {
		description "Initial revision of version 1";
	}

	grouping ecmp-paths {
		leaf maximum-paths {
			type uint16 {
				range 1..64; 
			}
			description "Equal-cost multi-path routing maximum paths number";
			configd:help "Equal-cost multi-path routing maximum paths number";
			configd:create "/opt/vyatta/share/tmplscripts/protocols/ecmp/maximum-paths/configd_create.sh";
			configd:delete "/opt/vyatta/share/tmplscripts/protocols/ecmp/maximum-paths/configd_delete.sh";
		}
	}

	grouping disable {
		leaf disable {
			type empty;
			description "Disable equal-cost multi-path routing";
			configd:help "Disable equal-cost multi-path routing";
			configd:create "/opt/vyatta/share/tmplscripts/protocols/ecmp/disable/configd_create.sh";
			configd:delete "/opt/vyatta/share/tmplscripts/protocols/ecmp/disable/configd_delete.sh";
		}
	}

	augment /protocols:protocols {
		container ecmp {
			configd:help "Equal-cost multi-path routing parameters";
			uses ecmp-paths;
			uses disable;
			leaf mode {
				type enumeration {
					enum "hrw" {
						configd:help "HRW equal-cost multi-path routing mode (default)";
					}
					enum "hash-threshold" {
						configd:help "Hash-threshold equal-cost multi-path routing mode";
					}
					enum "modulo-n" {
						configd:help "Modulo-n equal-cost multi-path routing mode";
					}
				}
				configd:help "Equal-cost multi-path routing mode";
				default "hrw";
				configd:update "/opt/vyatta/share/tmplscripts/protocols/ecmp/mode/configd_update.sh";
				configd:delete "/opt/vyatta/share/tmplscripts/protocols/ecmp/mode/configd_delete.sh";
			}
		}
	}
}
