module vyatta-protocols-bfd-v1 {
	namespace "urn:vyatta.com:mgmt:vyatta-protocols-bfd:1";
	prefix vyatta-protocols-bfd-v1;

	import vyatta-protocols-v1 {
		prefix protocols;
	}
	import vyatta-services-v1 {
		prefix service;
	}   
	import vyatta-service-snmp-v1 {
		prefix service-snmp;
	} 
	import vyatta-types-v1 {
		prefix types;
	}
	import configd-v1 {
		prefix configd;
	}
	import vyatta-interfaces-v1 {
		prefix if;
	}
	import vyatta-interfaces-dataplane-v1 {
		prefix interfaces-dataplane;
	}
	import vyatta-interfaces-bonding-v1 {
		prefix interfaces-bonding;
	}
	import vyatta-protocols-static-v1 {
		prefix protocols-static;
	}
	import vyatta-protocols-bgp-v1 {
		prefix protocols-bgp;
	}
	import vyatta-protocols-ospf-v1 {
		prefix protocols-ospf;
	}
	import vyatta-protocols-ospfv3-v1 {
		prefix protocols-ospfv3;
	}
	import vyatta-interfaces-tunnel-v1 {
		prefix interfaces-tunnel;
	}

	organization "Brocade Communications Systems, Inc.";
	contact
		"Brocade Communications Systems, Inc.
		 Postal: 130 Holger Way
		         San Jose, CA 95134
		 E-mail: support@Brocade.com
		 Web: www.brocade.com";

	description
		"Copyright (c) 2015-2016 by Brocade Communications Systems, Inc.
		 All rights reserved.

		 The YANG module package for vyatta-protocols-bfd-v1";

	revision 2016-06-01 {
		description "BFD yang script changes for OSPF on tunnels, IPv6 Bonded interfaces, enabling bfd traps and other bugfixes";
	}
	revision 2015-09-23 {
		description "Initial revision of version 1";
	}

	/* Defining Groupings, these groupings, akin to macros will be substituted where ever called */
	grouping enable-fall-over-bfd {
		container fall-over {
			description "This container is present only when fall-over is configured.";
			configd:help "Fall-over detection";
			leaf bfd {
				type empty;
				description "Enable Bidirectional Forwarding Detection (BFD)";
				configd:help "Bidirectional Forwarding Detection (BFD)";
			}
		}
	}

	grouping interface-template {
		container bfd {
			configd:priority "997";
			description "Configures BFD parameter template on interface.";
			configd:help "Bidirectional Forwarding Detection (BFD)";
			leaf template {
				type leafref {
					path "/protocols:protocols/vyatta-protocols-bfd-v1:bfd/vyatta-protocols-bfd-v1:template/vyatta-protocols-bfd-v1:tagnode";
				}
				description "Template definition to be referenced by sessions";
				configd:help "Template name";
				configd:create "/opt/vyatta/share/tmplscripts/interfaces/all/bfd/configd_create.sh";
				configd:delete "/opt/vyatta/share/tmplscripts/interfaces/all/bfd/configd_delete.sh";
			}
		}
	}

	grouping bfd-logging {
		container log {
			description "List of logging parameters for BFD";
			configd:help "BFD logging parameters";
			leaf all {
				type empty;
				description "Enable all BFD logs";
				configd:help "Enable all BFD logs";
				configd:create "/opt/vyatta/share/tmplscripts/protocols/bfd/log/configd_create.sh";
				configd:delete "/opt/vyatta/share/tmplscripts/protocols/bfd/log/configd_delete.sh";
			}
			leaf event {
				type empty;
				description "Enable event logs for BFD";
				configd:help "Enable BFD event logs";
				configd:create "/opt/vyatta/share/tmplscripts/protocols/bfd/log/configd_create.sh";
				configd:delete "/opt/vyatta/share/tmplscripts/protocols/bfd/log/configd_delete.sh";
			}
			leaf ipc-error {
				type empty;
				description "Enable ipc-error logs for BFD";
				configd:help "Enable BFD ipc-error logs";
				configd:create "/opt/vyatta/share/tmplscripts/protocols/bfd/log/configd_create.sh";
				configd:delete "/opt/vyatta/share/tmplscripts/protocols/bfd/log/configd_delete.sh";
			}
			leaf ipc-event {
				type empty;
				description "Enable ipc-event logs for BFD";
				configd:help "Enable BFD ipc-event logs";
				configd:create "/opt/vyatta/share/tmplscripts/protocols/bfd/log/configd_create.sh";
				configd:delete "/opt/vyatta/share/tmplscripts/protocols/bfd/log/configd_delete.sh";
			}
			leaf packet {
				type empty;
				description "Enable packet logs for BFD";
				configd:help "Enable BFD packet logs";
				configd:create "/opt/vyatta/share/tmplscripts/protocols/bfd/log/configd_create.sh";
				configd:delete "/opt/vyatta/share/tmplscripts/protocols/bfd/log/configd_delete.sh";
			}
			leaf session {
				type empty;
				description "Enable session logs for BFD";
				configd:help "Enable BFD session logs";
				configd:create "/opt/vyatta/share/tmplscripts/protocols/bfd/log/configd_create.sh";
				configd:delete "/opt/vyatta/share/tmplscripts/protocols/bfd/log/configd_delete.sh";
			}
		}
	}
	grouping session-template {
		list destination {
			configd:priority "999";
			description "Session template destination address";
			configd:help "Destination Address";
			configd:delete   "/opt/vyatta/share/tmplscripts/protocols/bfd/destination/configd_delete.sh";
			key "tagnode";
			leaf tagnode {
				description "Session template destination address";
				configd:help "Destination Address";
				type union {
					type types:ipv4-address;
					type types:ipv6-address;
				}
			}
			list source {
				min-elements "1";
				description "Session template source address";
				configd:help "Source Address";
				configd:create "/opt/vyatta/share/tmplscripts/protocols/bfd/destination/source/configd_create.sh";
				configd:delete "/opt/vyatta/share/tmplscripts/protocols/bfd/destination/source/configd_delete.sh";
				configd:end    "/opt/vyatta/share/tmplscripts/protocols/bfd/destination/source/configd_end.sh";
				key "tagnode";
				leaf tagnode {
					description "Session template source address";
					configd:help "Source Address";
					type union {
						type types:ipv4-address;
						type types:ipv6-address;
						type enumeration {
							enum "any";
						}
					}
				}
				leaf helper-session {
					type empty;
					description "Enable BFD session in Helper mode";
					configd:help	"Helper Session";
					must "((../tagnode) != 'any' )" {
						error-message "Helper session is not supported when source is 'any'";
					}
					configd:create   "/opt/vyatta/share/tmplscripts/protocols/bfd/destination/source/helper-session/configd_create.sh";
					configd:delete   "/opt/vyatta/share/tmplscripts/protocols/bfd/destination/source/helper-session/configd_delete.sh";
				}
				leaf template {
					type leafref {
						path "/protocols:protocols/vyatta-protocols-bfd-v1:bfd/vyatta-protocols-bfd-v1:template/vyatta-protocols-bfd-v1:tagnode";
					}
					description	"Template to be referenced by Session";
					configd:help	"Template name";
					configd:create   "/opt/vyatta/share/tmplscripts/protocols/bfd/destination/source/template/configd_create.sh";
				}
			}
		}
	}

	/* Augmenting protocols-static */
	augment /protocols:protocols/protocols-static:static/protocols-static:route/protocols-static:next-hop {
		uses enable-fall-over-bfd;
	}

	augment /protocols:protocols/protocols-static:static/protocols-static:route6/protocols-static:next-hop {
		uses enable-fall-over-bfd;
	}

	/* Augmenting protocols-bgp */
	augment /protocols:protocols/protocols-bgp:bgp/protocols-bgp:neighbor {
		uses enable-fall-over-bfd;
	}

	/* Augmenting protocols */
	augment /protocols:protocols/protocols-ospf:ospf/protocols-ospf:area/protocols-ospf:virtual-link {
		uses enable-fall-over-bfd {
			refine fall-over/bfd {
				configd:create "/opt/vyatta/share/tmplscripts/protocols/all/fall-over/bfd/configd_create.sh";
				configd:delete "/opt/vyatta/share/tmplscripts/protocols/all/fall-over/bfd/configd_delete.sh";
			}
		}
	}

	augment /protocols:protocols/protocols-ospfv3:ospfv3/protocols-ospfv3:area/protocols-ospfv3:virtual-link {
                uses enable-fall-over-bfd {
                        refine fall-over/bfd {
				configd:create "/opt/vyatta/share/tmplscripts/protocols/all/fall-over/bfd/configd_create.sh";
				configd:delete "/opt/vyatta/share/tmplscripts/protocols/all/fall-over/bfd/configd_delete.sh";
                        }
                }
	}

	augment /protocols:protocols/protocols-ospfv3:ospfv3/protocols-ospfv3:process/protocols-ospfv3:area/protocols-ospfv3:virtual-link {
		uses enable-fall-over-bfd {
			refine fall-over/bfd {
				configd:create "/opt/vyatta/share/tmplscripts/protocols/all/fall-over/bfd/configd_create.sh";
				configd:delete "/opt/vyatta/share/tmplscripts/protocols/all/fall-over/bfd/configd_delete.sh";
			}
		}
	}

	/* Augmenting IP interfaces */
	augment /if:interfaces/interfaces-dataplane:dataplane/interfaces-dataplane:ip/protocols-ospf:ospf {
		uses enable-fall-over-bfd {
			refine fall-over/bfd {
				configd:create "/opt/vyatta/share/tmplscripts/interfaces/all/ip/ospf/fall-over/bfd/configd_create.sh";
				configd:delete "/opt/vyatta/share/tmplscripts/interfaces/all/ip/ospf/fall-over/bfd/configd_delete.sh";
			}
		}
	}

	/* Augmenting interface level parameter template */
	augment /if:interfaces/interfaces-dataplane:dataplane {
		uses interface-template;
	}

	/* Augmenting interface level parameter template */
	augment /if:interfaces/interfaces-dataplane:dataplane/interfaces-dataplane:vif {
		uses interface-template;
	}

	augment /if:interfaces/interfaces-dataplane:dataplane/interfaces-dataplane:vif/interfaces-dataplane:ip/protocols-ospf:ospf {
		uses enable-fall-over-bfd {
			refine fall-over/bfd {
				configd:create "/opt/vyatta/share/tmplscripts/interfaces/all/ip/ospf/fall-over/bfd/configd_create.sh";
				configd:delete "/opt/vyatta/share/tmplscripts/interfaces/all/ip/ospf/fall-over/bfd/configd_delete.sh";
			}
		}
	}

	/* Augmenting interface level parameter template */
	augment /if:interfaces/interfaces-tunnel:tunnel {
		uses interface-template;
	}

	augment /if:interfaces/interfaces-tunnel:tunnel/interfaces-tunnel:ip/protocols-ospf:ospf {
		uses enable-fall-over-bfd {
			refine fall-over/bfd {
				configd:create "/opt/vyatta/share/tmplscripts/interfaces/all/ip/ospf/fall-over/bfd/configd_create.sh";
				configd:delete "/opt/vyatta/share/tmplscripts/interfaces/all/ip/ospf/fall-over/bfd/configd_delete.sh";
			}
		}
	}

	/* Augmenting IPv6 interfaces */
	augment /if:interfaces/interfaces-dataplane:dataplane/interfaces-dataplane:ipv6/protocols-ospfv3:ospfv3 {
		uses enable-fall-over-bfd {
			refine fall-over/bfd {
				configd:create "/opt/vyatta/share/tmplscripts/interfaces/all/ipv6/ospfv3/fall-over/bfd/configd_create.sh";
				configd:delete "/opt/vyatta/share/tmplscripts/interfaces/all/ipv6/ospfv3/fall-over/bfd/configd_delete.sh";
			}
		}

	}

	augment /if:interfaces/interfaces-dataplane:dataplane/interfaces-dataplane:vif/interfaces-dataplane:ipv6/protocols-ospfv3:ospfv3 {
		uses enable-fall-over-bfd {
			refine fall-over/bfd {
				configd:create "/opt/vyatta/share/tmplscripts/interfaces/all/ipv6/ospfv3/fall-over/bfd/configd_create.sh";
				configd:delete "/opt/vyatta/share/tmplscripts/interfaces/all/ipv6/ospfv3/fall-over/bfd/configd_delete.sh";
			}
		}
	}

	augment /if:interfaces/interfaces-tunnel:tunnel/interfaces-tunnel:ipv6/protocols-ospfv3:ospfv3 {
		uses enable-fall-over-bfd {
			refine fall-over/bfd {
				configd:create "/opt/vyatta/share/tmplscripts/interfaces/all/ipv6/ospfv3/fall-over/bfd/configd_create.sh";
				configd:delete "/opt/vyatta/share/tmplscripts/interfaces/all/ipv6/ospfv3/fall-over/bfd/configd_delete.sh";
			}
		}
	}

	/* Augmenting bonding interfaces */
	augment /if:interfaces/interfaces-bonding:bonding/interfaces-bonding:ip/protocols-ospf:ospf {
		uses enable-fall-over-bfd {
			refine fall-over/bfd {
				configd:create "/opt/vyatta/share/tmplscripts/interfaces/all/ip/ospf/fall-over/bfd/configd_create.sh";
				configd:delete "/opt/vyatta/share/tmplscripts/interfaces/all/ip/ospf/fall-over/bfd/configd_delete.sh";
			}
		}
	}

	augment /if:interfaces/interfaces-bonding:bonding/interfaces-bonding:ipv6/protocols-ospfv3:ospfv3 {
		uses enable-fall-over-bfd {
			refine fall-over/bfd {
				configd:create "/opt/vyatta/share/tmplscripts/interfaces/all/ipv6/ospfv3/fall-over/bfd/configd_create.sh";
				configd:delete "/opt/vyatta/share/tmplscripts/interfaces/all/ipv6/ospfv3/fall-over/bfd/configd_delete.sh";
			}
		}
	}

	augment /if:interfaces/interfaces-bonding:bonding {
		uses interface-template;
	}

	augment /if:interfaces/interfaces-bonding:bonding/interfaces-bonding:vif/interfaces-bonding:ip/protocols-ospf:ospf {
		uses enable-fall-over-bfd {
			refine fall-over/bfd {
				configd:create "/opt/vyatta/share/tmplscripts/interfaces/all/ip/ospf/fall-over/bfd/configd_create.sh";
				configd:delete "/opt/vyatta/share/tmplscripts/interfaces/all/ip/ospf/fall-over/bfd/configd_delete.sh";
			}
		}
	}

	augment /if:interfaces/interfaces-bonding:bonding/interfaces-bonding:vif/interfaces-bonding:ipv6/protocols-ospfv3:ospfv3 {
		uses enable-fall-over-bfd {
			refine fall-over/bfd {
				configd:create "/opt/vyatta/share/tmplscripts/interfaces/all/ipv6/ospfv3/fall-over/bfd/configd_create.sh";
				configd:delete "/opt/vyatta/share/tmplscripts/interfaces/all/ipv6/ospfv3/fall-over/bfd/configd_delete.sh";
			}
		}
	}

	augment /if:interfaces/interfaces-bonding:bonding/interfaces-bonding:vif {
		uses interface-template;
	}

	/* Augmenting trap notifications */
	augment /service:service/service-snmp:snmp/service-snmp:notification {
		container bfd {
			description "Enable BFD specific SNMP Notifications";
			configd:help "BFD Notifications";
			leaf all {
				type empty;
				description "Enable BFD specific SNMP Notifications";
				configd:help "BFD Notifications";
				configd:create "vtysh -c \"configure terminal\" -c \"bfd notification all\"";
				configd:delete "vtysh -c \"configure terminal\" -c \"no bfd notification\"";
			}
		}
	}

	/* BFD commands' definition */
	augment /protocols:protocols {
		container bfd {
			description "The BFD node need not exist if neither BFD templates nor BFD destinations are configured";
			presence "true";
			configd:priority "990";
			configd:help "BFD protocol";
			configd:end "/opt/vyatta/share/tmplscripts/protocols/bfd/configd_end.sh";
			list template {
				configd:priority "995";
				description "Definition of Template that would be referenced by Session.";
				configd:help "Template name.";
				key "tagnode";
				leaf tagnode {
					type string;
					description "Name of the Template to be referenced.";
					configd:help "Template name.";
					configd:create "/opt/vyatta/share/tmplscripts/protocols/bfd/template/configd_create.sh";
					configd:delete "/opt/vyatta/share/tmplscripts/protocols/bfd/template/configd_delete.sh";
				}
				container auth {
					description "This container is present only authentication is enabled.";
					configd:priority "996";
					configd:help "Authentication";
					configd:delete "/opt/vyatta/share/tmplscripts/protocols/bfd/template/auth/configd_delete.sh";
					container simple {
						description "This container is present only when simple text password is configured.";
						configd:help "Simple Password";
						leaf key {
							description "Authentication key chain";
							configd:help "Authentication key chain";
							configd:secret "true";
							type string {
								pattern '[^\t\n\r ]{1,16}' {
									error-message "Simple password must be 16 characters or less";
								}
							}
							configd:create "/opt/vyatta/share/tmplscripts/protocols/bfd/template/auth/simple/key/configd_create.sh";
						}
					}
				}
				leaf minimum-tx {
					configd:priority "996";
					description "Desired Minimum transmit interval ( in milliseconds )";
					configd:help "Minimum transmit interval ( in milliseconds )";
					configd:create "/opt/vyatta/share/tmplscripts/protocols/bfd/template/minimum-tx/configd_create.sh";
					configd:delete "/opt/vyatta/share/tmplscripts/protocols/bfd/template/minimum-tx/configd_delete.sh";
					type uint32 {
						range 20..10000;
					}
					default "300";
				}
				leaf minimum-rx {
					configd:priority "996";
					description "Required Minimum receive interval ( in milliseconds )";
					configd:help "Minimum receive interval ( in milliseconds )";
					configd:create "/opt/vyatta/share/tmplscripts/protocols/bfd/template/minimum-rx/configd_create.sh";
					configd:delete "/opt/vyatta/share/tmplscripts/protocols/bfd/template/minimum-rx/configd_delete.sh";
					type uint32 {
						range 20..10000;
					}
					default "300";
				}
				leaf multiplier {
					configd:priority "996";
					description "Detection Time Multiplier";
					configd:help "Detect Multiplier";
					configd:create "/opt/vyatta/share/tmplscripts/protocols/bfd/template/multiplier/configd_create.sh";
					configd:delete "/opt/vyatta/share/tmplscripts/protocols/bfd/template/multiplier/configd_delete.sh";
					type uint32 {
						range 1..100;
					}
					default "3";
				}
			}
			uses session-template;
			uses bfd-logging;
		}
	}
}
