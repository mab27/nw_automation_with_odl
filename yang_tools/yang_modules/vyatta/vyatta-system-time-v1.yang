module vyatta-system-time-v1 {
	namespace "urn:vyatta.com:mgmt:vyatta-system-time:1";
	prefix vyatta-system-time-v1;

	import vyatta-system-v1 {
		prefix system;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 NTP configuration";

	revision 2016-10-27 {
		description "Deprecate the dynamic option for ntp.";
	}
	revision 2016-06-16 {
		description "Use a grouping for ntp. Needed for vrf support.";
	}
	revision 2015-12-04 {
		description "Add description to time-zone.";
	}
	revision 2015-08-14 {
		description "Initial revision of version 1.";
	}

	grouping system-time-ntp {
		container ntp {
			presence "true";
			configd:priority "300";
			configd:help "Network Time Protocol (NTP) configuration";
			configd:validate "/opt/vyatta/share/tmplscripts/system/ntp/configd_validate_ntpkeys";
			configd:create "/opt/vyatta/sbin/vyatta_configure_ntp.pl --operation=start";
			configd:delete "/opt/vyatta/sbin/vyatta_configure_ntp.pl --operation=stop";
			configd:update "/opt/vyatta/sbin/vyatta_configure_ntp.pl --operation=restart";

			leaf statistics {
				type empty;
				configd:help "Enable statistics collection";
			}
			list keyid {
				configd:help "Network Time Protocol (NTP) authentication key";
				key "tagnode";
				leaf tagnode {
					type uint16 {
						range 1..65535;
					}
					configd:help "NTP authentication key ID";
				}
				leaf digest {
					type enumeration {
						enum md5;
						enum sha1;
					}
					default md5;
					configd:help "Digest Algorithm for authentication";
				}
				leaf plaintext-password {
					type string {
						length "1..20";
						pattern '([^\s#])+';
					}
					mandatory true;
					configd:secret "true";
					configd:help "Plaintext password for authentication (max 20 characters)";
				}
			}
			list server {
				configd:help "Network Time Protocol (NTP) server";
				key "tagnode";
				leaf tagnode {
					type string;
					configd:help "Network Time Protocol (NTP) server";
				}
				leaf preempt {
					type empty;
					configd:help "Specifies the association as preemptable rather than the default persistent";
				}
				leaf dynamic {
					status deprecated;
					type empty;
					configd:help "Allow server to be configured even if not reachable";
				}
				leaf noselect {
					type empty;
					configd:help "Marks the server as unused";
				}
				leaf prefer {
					type empty;
					configd:help "Marks the server as preferred";
				}
				leaf address-family {
					type enumeration {
						enum ipv4 {
							configd:help "only IPv4 addresses";
						}
						enum ipv6 {
							configd:help "only IPv6 addresses";
						}
					}
					configd:help "Address family for hostname resolution";
				}
				leaf keyid {
					type uint16 {
						range 1..65535;
					}
					configd:help "NTP authentication key ID";
				}
			}
		}
	}

	augment /system:system {
		uses system-time-ntp;
		leaf time-zone {
			type string;
			description "Local time zone as specified by Region/City";
			configd:priority "100";
			configd:help "Local time zone";
			default "GMT";
			configd:update "/opt/vyatta/share/tmplscripts/system/time-zone/configd_update.sh";
			configd:allowed "/opt/vyatta/share/tmplscripts/system/time-zone/configd_allowed.sh";
			configd:end "/opt/vyatta/share/tmplscripts/system/time-zone/configd_end.sh";
			configd:delete "/opt/vyatta/share/tmplscripts/system/time-zone/configd_delete1.cli";
		}
	}
}
