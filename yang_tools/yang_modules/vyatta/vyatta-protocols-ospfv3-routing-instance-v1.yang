module vyatta-protocols-ospfv3-routing-instance-v1 {
	namespace "urn:vyatta.com:mgmt:vyatta-protocols-ospfv3-routing-instance:1";
	prefix vyatta-protocols-ospfv3-routing-instance-v1;

	import configd-v1 {
		prefix configd;
	}
	import vyatta-routing-v1 {
		prefix routing-instance;
	}
	import vyatta-protocols-ospfv3-v1 {
		prefix ospfv3;
	}
	import vyatta-protocols-v1 {
		prefix protocols;
	}
	import vyatta-protocols-interface-validation-routing-instance-v1 {
		prefix if-validation-routing-inst;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for
		 vyatta-protocols-ospfv3-routing-instance-v1";

	revision 2016-10-24 {
		description "add description to all yang nodes";
	}

	revision 2016-07-27 {
		description "added validation for duplicate router-id,
			Add Routing Instance support for OSPFv3";
	}

	augment /routing-instance:routing/routing-instance:routing-instance/routing-instance:protocols {
		container ospfv3 {
			configd:help "Open Shortest Path First version 3 protocol (OSPFv3) parameters";
			description "Open Shortest Path First version 3 protocol (OSPFv3) parameters";
			list process {
				description "Open Shortest Path First version 3 (OSPFv3) process list";
				configd:help "OSPFv3 process name";
				configd:update "/opt/vyatta/share/tmplscripts/protocols/ospfv3/process/configd_update.sh";
				configd:delete "/opt/vyatta/share/tmplscripts/protocols/ospfv3/process/configd_delete.sh";
				max-elements "1";
				key "process-name";
				leaf process-name {
					type string {
						pattern '[0-9A-Za-z][-_0-9A-Za-z]*' {
							error-message "name must be alphanumeric (hyphen/underscore may be used inside)";
						}
					}
					must "not((current() = /protocols:protocols/ospfv3:ospfv3/ospfv3:process/ospfv3:tagnode)"
                                                + "or (count(/routing-instance:routing/routing-instance:routing-instance/routing-instance:protocols/ospfv3/process[process-name = current()]) > 1))" {
						error-message "Instance is already bound to another routing-instance";
					}
					description "OSPFv3 process name";
					configd:help "OSPFv3 process name";
				}
				uses ospfv3:spf-timers;
				uses ospfv3:ospfv3-distribute-list;
				uses ospfv3:ospfv3-generic-parameters;
				uses ospfv3:ospfv3-redistribute;
				uses ospfv3:ospfv3-distance;
				uses ospfv3:ospfv3-abr-type;
				uses ospfv3:ospfv3-ipv6-summary-address;
				uses ospfv3:ospfv3-default-information;
				uses ospfv3:ospfv3-ipv4-address-family {
					refine address-family/ipv4/unicast/area/range/advertise {
						must "not(../not-advertise)" {
							error-message "Only one of advertise or not-advertise can be configured";
						}
					}
				}
				uses ospfv3:ospfv3-area {
					refine area/range/advertise {
						must "not(../not-advertise)" {
							error-message "Only one of advertise or not-advertise can be configured";
						}
					}
				}
				uses ospfv3:ospfv3-generic-parameters-1 {
					refine router-id {
						must "count(/protocols:protocols/ospfv3:ospfv3[ospfv3:router-id = current()]"
							+ "| /protocols:protocols/ospfv3:ospfv3/ospfv3:process[ospfv3:router-id = current()]"
							+ "| /routing-instance:routing/routing-instance:routing-instance/routing-instance:protocols/ospfv3/process[router-id = current()]) <= 1" {
							error-message "Router-id is used by another process in router";
						}
					}
				}
				uses ospfv3:ospfv3-debug-parameters;
				uses if-validation-routing-inst:ospf-passive-intf-routing-inst {
					refine "passive-interface" {
						configd:help "Suppress routing updates on an interface";
						description "Suppress routing updates on an interface";
						configd:priority "642";
						must 'not(starts-with(current(), "ers"))' {
							error-message "Can't configure passive-interface on erspan interfaces";
						}
						configd:allowed "/opt/vyatta/sbin/vyatta-interfaces.pl --show all --filter-out ^ers && echo default";
						configd:create "/opt/vyatta/share/tmplscripts/protocols/ospfv3/passive-interface/configd_create.sh";
						configd:delete "/opt/vyatta/share/tmplscripts/protocols/ospfv3/passive-interface/configd_delete.sh";
					}
				}
				uses if-validation-routing-inst:ospf-passive-intf-exclude-routing-inst {
					refine "passive-interface-exclude" {
						configd:help "Excludes OSPFv3 routing update suppression on an interface";
						description "Excludes OSPFv3 routing update suppression on an interface";
						configd:priority "643";
						must 'not(starts-with(current(), "ers"))' {
							error-message "Can't configure passive-interface-exclude on erspan interfaces";
						}
						configd:create "/opt/vyatta/share/tmplscripts/protocols/ospfv3/passive-interface/exclude/configd_create.sh";
						configd:delete "/opt/vyatta/share/tmplscripts/protocols/ospfv3/passive-interface/exclude/configd_delete.sh";
					}
				}
			}
		}
	}
}
