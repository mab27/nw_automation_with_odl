module vyatta-multicast-routing-instance-v1 {
	namespace "urn:vyatta.com:mgmt:vyatta-multicast-routing-instance:1";
	prefix vyatta-multicast-routing-instance-v1;

	import configd-v1 {
		prefix configd;
	}
	import vyatta-routing-v1 {
		prefix routing;
	}
	import vyatta-multicast-v1 {
		prefix multicast;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-multicast-routing-instance-v1-yang";

	revision 2016-04-21 {
		description "Add Routing Instance support for multicast 
			Augment /routing/routing-instance/protocols";
	}

		augment /routing:routing/routing:routing-instance/routing:protocols {
			uses multicast:multicast-parameters {
			refine multicast/ip {
				configd:end "vyatta-multicast 4 --routing-instance $VAR(../../../@)";
			}
			refine multicast/ipv6 {
				configd:end "vyatta-multicast 6 --routing-instance $VAR(../../../@)";
			}
		}
	}
}
