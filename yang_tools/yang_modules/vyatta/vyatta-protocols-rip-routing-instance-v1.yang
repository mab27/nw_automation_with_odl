module vyatta-protocols-rip-routing-instance-v1 {
	namespace "urn:vyatta.com:mgmt:vyatta-protocols-rip-routing-instance:1";
	prefix vyatta-protocols-rip-routing-instance-v1;

	import vyatta-routing-v1 {
		prefix routing-instance;
	}
	import vyatta-protocols-rip-v1 {
		prefix rip;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for vyatta-protocols-rip-routing-instance-v1";

	revision 2016-05-12 {
		 description "Initial revision of Routing-instance support";
	}

	augment /routing-instance:routing/routing-instance:routing-instance/routing-instance:protocols {
		uses rip:rip-protocol;
	}
	augment /routing-instance:routing/routing-instance:routing-instance/routing-instance:protocols/rip/log {
		uses rip:rip-log-packet;
	}
}
