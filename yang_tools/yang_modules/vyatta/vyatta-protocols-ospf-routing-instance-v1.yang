module vyatta-protocols-ospf-routing-instance-v1 {
	namespace "urn:vyatta.com:mgmt:vyatta-protocols-ospf-routing-instance:1";
	prefix vyatta-protocols-ospf-routing-instance-v1;

	import vyatta-protocols-v1 {
		prefix protocols;
	}
	import configd-v1 {
		prefix configd;
	}
	import vyatta-routing-v1 {
		prefix routing-instance;
	}
	import vyatta-protocols-interface-validation-routing-instance-v1 {
		prefix if-validation-routing-inst;
	}
	import vyatta-protocols-ospf-v1 {
		prefix ospf;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for vyatta-protocols-ospf-routing-instance-v1";

	revision 2016-10-10 {
		description "Adding ospfv2 multi process support";
	}

	revision 2016-07-21 {
		description "Add Routing Instance support for OSPF"; 
	}

	augment /routing-instance:routing/routing-instance:routing-instance/routing-instance:protocols {
		container ospf {
			description "OSPFv2 support for VRF";
			configd:help "OSPFv2 support for VRF";
			list process {
				configd:help "OSPF Process ID";
				configd:create "/opt/vyatta/share/tmplscripts/protocols/ospf/configd_create.cli";
				configd:delete "/opt/vyatta/share/tmplscripts/protocols/ospf/configd_delete.cli";
				description "OSPF Process ID";
				key instance;
				leaf instance {
					type uint16 {
						range 1..65535;
					}
					must "count(/protocols:protocols/ospf:ospf/ospf:process[ospf:instance = current()] | " +
						"/routing-instance:routing/routing-instance:routing-instance/routing-instance:protocols/ospf/process[instance = current()]) <= 1" {
						error-message "Instance already bound to another VRF";
					}
				}
				uses ospf:ospf-parameters {
					refine parameters/router-id {
						must "count(/protocols:protocols/ospf:ospf/ospf:parameters[ospf:router-id = current()] | " +
							"/protocols:protocols/ospf:ospf/ospf:process/ospf:parameters[ospf:router-id = current()] | " +
							"/routing-instance:routing/routing-instance:routing-instance/routing-instance:protocols/ospf/process/parameters[router-id = current()]) <= 1" {
								error-message "Router-id is used by another process in router";
						}
					}
				}
				uses ospf:ospf-parameters-all;
				uses ospf:ospf-debug-parameters;
				uses if-validation-routing-inst:ospf-passive-intf-routing-inst {
					refine passive-interface {
						configd:priority "621";
						must 'not(starts-with(current(), "ers"))' {
							error-message "Can't configure passive-interface on erspan interfaces";
						}
						configd:help "Suppress routing updates on an interface";
						description "Suppress routing updates on an interface";
						configd:allowed "/opt/vyatta/sbin/vyatta-interfaces.pl --show all --filter-out ^ers && echo default";
						configd:create "/opt/vyatta/share/tmplscripts/protocols/ospf/passive-interface/configd_create.cli";
						configd:delete "/opt/vyatta/share/tmplscripts/protocols/ospf/passive-interface/configd_delete.cli";
					}
				}
				uses if-validation-routing-inst:ospf-passive-intf-exclude-routing-inst {
					refine passive-interface-exclude {
						configd:priority "622";
						must 'not(starts-with(current(), "ers"))' {
							error-message "Can't configure passive-interface-exclude on erspan interfaces";
						}
						configd:help "Excludes OSPF routing update suppression on an interface";
						description "Excludes OSPF routing update suppression on an interface";
						configd:create "/opt/vyatta/share/tmplscripts/protocols/ospf/passive-interface/exclude/configd_create.cli";
						configd:delete "/opt/vyatta/share/tmplscripts/protocols/ospf/passive-interface/exclude/configd_delete.cli";
					}
				}
			}
		}
	}
}
