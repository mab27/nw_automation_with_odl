module vyatta-protocols-pim-routing-instance-v1 {
	namespace "urn:vyatta.com:mgmt:vyatta-protocols-pim-routing-instance:1";
	prefix vyatta-protocols-pim-routing-instance-v1;

	import configd-v1 {
		prefix configd;
	}
	import vyatta-routing-v1 {
		prefix routing;
	}
	import vyatta-protocols-pim-v1 {
		prefix pim;
	}
	import vyatta-routing-instance-interfaces-v1 {
		prefix rif;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-protocols-pim-routing-instance-v1";

	revision 2016-04-18 {
		description "Add Routing Instance support for pim 
			Augment /routing/routing-instance/protocols";
	}

	augment /routing:routing/routing:routing-instance/routing:protocols {
		uses pim:pim-parameters {
			refine pim {
				configd:end "vyatta-pim 4 --routing-instance $VAR(../../@)";
			}
			refine pim/register-source/interface {
				must "current() = /routing:routing/routing:routing-instance" +
						"[routing:instance-name = current()/../../../../routing:instance-name]" +
						"/rif:interface/rif:name" {
					error-message "Interface must be configured in this routing instance";
				}
			}
			refine pim/bsr-candidate/interface {
				must "current() = /routing:routing/routing:routing-instance" +
						"[routing:instance-name = current()/../../../../routing:instance-name]" +
						"/rif:interface/rif:name" {
					error-message "Interface must be configured in this routing instance";
				}
			}
			refine pim/rp-candidate/interface {
				must "current()/tagnode = /routing:routing/routing:routing-instance" +
						"[routing:instance-name = current()/../../../../routing:instance-name]" +
						"/rif:interface/rif:name" {
					error-message "Interface must be configured in this routing instance";
				}
			}
		}
	}
}
