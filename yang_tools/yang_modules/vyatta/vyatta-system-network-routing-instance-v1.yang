module vyatta-system-network-routing-instance-v1 {
	namespace "urn:vyatta.com:mgmt:vyatta-system-network-routing-instance:1";
	prefix vyatta-system-network-routing-instance-v1;

	import configd-v1 {
		prefix configd;
	}
	import vyatta-routing-v1 {
		prefix rt-instance;
	}
	import vyatta-system-network-v1 {
		prefix sys-network;
	}

	organization "Brocade Communications Systems, Inc.";
	contact
		"Brocade Communications Systems, Inc.
		Postal: 130 Holger Way
			San Jose, CA 95134
		E-mail: support@Brocade.com
		Web: www.brocade.com";

	description
		"Copyright (c) 2016 by Brocade Communications Systems, Inc.
		 All rights reserved.

		 The YANG module for vyatta-system-network-routing-instance-v1";

	revision 2016-05-31 {
		description "Support DNS subset of system-network.";
	}

	revision 2016-04-18 {
		description "VRF support for DNS domain.";
	}

	augment /rt-instance:routing/rt-instance:routing-instance/rt-instance:system {
		uses sys-network:system-network-domain {
			refine domain-name {
				description "Configure domain name for dns resolver in routing instance";
				configd:update "/opt/vyatta/share/tmplscripts/system/domain-name/configd_update.sh --vrf=$VAR(../../@)";
				configd:delete "/opt/vyatta/share/tmplscripts/system/domain-name/configd_delete.sh --vrf=$VAR(../../@)";
			}
			refine domain-search {
				description "Search list for host-name lookup in routing instance";
			}
			refine domain-search/domain {
				description "Domain name in search order for routing instance";
				configd:create "/opt/vyatta/share/tmplscripts/system/domain-search/domain/configd_create2";
				configd:delete "/opt/vyatta/share/tmplscripts/system/domain-search/domain/configd_delete2";
			}
		}
		uses sys-network:system-network-name-server-static-hosts {
			refine name-server {
				description "Name server list for domain lookup in routing instance";
				configd:create "/opt/vyatta/share/tmplscripts/system/name-server/configd_create2";
				configd:delete "/opt/vyatta/share/tmplscripts/system/name-server/configd_delete2";
			}
			refine static-host-mapping/host-name/inet {
				mandatory "true";
			}                       
		}
	}                       
}
