module vyatta-protocols-nsm-routing-instance-v1 {
	namespace "urn:vyatta.com:mgmt:vyatta-protocols-nsm-routing-instance:1";
	prefix vyatta-protocols-nsm-routing-instance-v1;

	import configd-v1 {
		prefix configd;
	}
	import vyatta-routing-v1 {
		prefix routing-instance;
	}
	import vyatta-protocols-nsm-v1 {
		prefix nsm;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for vyatta-protocols-nsm-routing-instance-v1";

	revision 2016-05-18 {
		description "Initial revision of Routing-instance support";
	}

	augment /routing-instance:routing/routing-instance:routing-instance/routing-instance:protocols {
		container nsm {
			configd:help "NSM parameters";
			configd:priority "650";
			container log {
				configd:help "NSM logging parameters";
				uses nsm:nsm-log-basic;
			}
		}
	}
}
