module vyatta-service-telnet-routing-instance-v1 {
	namespace "urn:vyatta.com:mgmt:vyatta-service-telnet-routing-instance:1";
	prefix vyatta-service-telnet-routing-instance-v1;

	import configd-v1 {
		prefix configd;
	}
	import vyatta-routing-v1 {
		prefix rt-instance;
	}
	import vyatta-service-telnet-v1 {
		prefix service-telnet;
	}

	organization "Brocade Communications Systems, Inc.";
	contact	"Brocade Communications Systems, Inc.
		 Postal: 130 Holger Way
		         San Jose, CA 95134
		 E-mail: support@Brocade.com
		 Web: www.brocade.com";

	description
		"Copyright (c) 2016 by Brocade Communications Systems, Inc.
		 All rights reserved.

		 Telnet configuration in VRF";

	revision 2016-04-18 {
		description "Initial revision of version 1.";
	}

	augment /rt-instance:routing/rt-instance:routing-instance/rt-instance:service {
		container telnet {
			presence "enable telnet";
			description "Telnet service in routing-instance";
			configd:priority "500";
			configd:help "Enable/disable Network Virtual Terminal Protocol (TELNET) protocol";
			configd:delete "vyatta_update_telnet --vrf=$VAR(../../../routing-instance/@) --operation=disable";
			configd:end "/opt/vyatta/share/tmplscripts/service/telnet/configd_end.sh";
			uses service-telnet:telnet-service-grouping;
		}
	}
}
