module vyatta-services-v1 {
	namespace "urn:vyatta.com:mgmt:vyatta-services:1";
	prefix vyatta-services-v1;

	import configd-v1 { prefix configd; }

	organization "Brocade Communications Systems, Inc.";
	contact
		"Brocade Communications Systems, Inc.
		 Postal: 130 Holger Way
		 	 San Jose, CA 95134
		 E-mail: support@Brocade.com
		 Web: www.brocade.com";

	description
		"Copyright (c) 2014-2016 by Brocade Communications Systems, Inc.
		 All rights reserved.

		 This module implements vyatta-services-v1.";

	revision 2015-08-05 {
		description "Initial revision of version 1.";
	}

	container service {
		configd:help "Services";
	}
}
