module vyatta-protocols-nsm-v1 {
	namespace "urn:vyatta.com:mgmt:vyatta-protocols-nsm:1";
	prefix vyatta-protocols-nsm-v1;

	import vyatta-protocols-v1 {
		prefix protocols;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2015-2016 by Brocade Communications Systems, Inc.
		 All rights reserved.

		 The YANG module package for vyatta-protocols-nsm-v1";

	revision 2016-05-18 {
		description "Group containers nsm";
	}

	revision 2015-08-06 {
		description "Initial revision of version 1";
	}

	grouping nsm-log-basic {
		leaf all {
			type empty;
				configd:help "Enable all NSM logs";
				configd:create "/opt/vyatta/share/tmplscripts/protocols/nsm/log/configd_create.sh";
				configd:delete "/opt/vyatta/share/tmplscripts/protocols/nsm/log/configd_delete.sh";
		}
		leaf events {
			type empty;
				configd:help "Enable NSM events logs";
				configd:create "/opt/vyatta/share/tmplscripts/protocols/nsm/log/configd_create.sh";
				configd:delete "/opt/vyatta/share/tmplscripts/protocols/nsm/log/configd_delete.sh";
		}
		leaf kernel {
			type empty;
				configd:help "Enable NSM kernel logs";
				configd:create "/opt/vyatta/share/tmplscripts/protocols/nsm/log/configd_create.sh";
				configd:delete "/opt/vyatta/share/tmplscripts/protocols/nsm/log/configd_delete.sh";
		}
	}
	grouping nsm-log-infra {
		container nsm {
			configd:priority "650";
			configd:help "NSM parameters";
			container log {
				configd:help "NSM logging parameters";
				uses nsm-log-basic;
				container ha {
					configd:help "NSM HA logs";
					leaf all {
						type empty;
						configd:help "Enable NSM HA logs";
						configd:create "/opt/vyatta/share/tmplscripts/protocols/nsm/log/ha/configd_create.sh";
						configd:delete "/opt/vyatta/share/tmplscripts/protocols/nsm/log/ha/configd_delete.sh";
					}
				}
				container packet {
					configd:help "NSM packet logs";
					leaf all {
						type empty;
						configd:help "Enable NSM packet all logs";
						configd:create "/opt/vyatta/share/tmplscripts/protocols/nsm/log/packet/configd_create.sh";
					 	configd:delete "/opt/vyatta/share/tmplscripts/protocols/nsm/log/packet/configd_delete.sh";
					}
					leaf detail {
						type empty;
						configd:help "Enable NSM packet detail logs";
						configd:create "/opt/vyatta/share/tmplscripts/protocols/nsm/log/packet/configd_create.sh";
						configd:delete "/opt/vyatta/share/tmplscripts/protocols/nsm/log/packet/configd_delete.sh";
					}
					leaf send {
						type empty;
						configd:help "Enable NSM packet send logs";
						configd:create "/opt/vyatta/share/tmplscripts/protocols/nsm/log/packet/configd_create.sh";
						configd:delete "/opt/vyatta/share/tmplscripts/protocols/nsm/log/packet/configd_delete.sh";
					}
					leaf recv {
						type empty;
						configd:help "Enable NSM packet recv logs";
						configd:create "/opt/vyatta/share/tmplscripts/protocols/nsm/log/packet/configd_create.sh";
						configd:delete "/opt/vyatta/share/tmplscripts/protocols/nsm/log/packet/configd_delete.sh";
					}
				}
			}
		}
	}
	augment /protocols:protocols {
		uses nsm-log-infra;
	}
}
