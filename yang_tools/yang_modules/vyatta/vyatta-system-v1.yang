module vyatta-system-v1 {
	namespace "urn:vyatta.com:mgmt:vyatta-system:1";
	prefix vyatta-system-v1;

	import configd-v1 { prefix configd; }
	import ietf-yang-types { prefix ytypes; }

	organization "Brocade Communications Systems, Inc.";
	contact
		"Brocade Communications Systems, Inc.
		 Postal: 130 Holger Way
		 	 San Jose, CA 95134
		 E-mail: support@Brocade.com
		 Web: www.brocade.com";

	description
		"Copyright (c) 2014-2017 by Brocade Communications Systems, Inc.
		 All rights reserved.

		 The YANG module for vyatta-system-v1-yang";

	revision 2017-01-24 {
		description "Add reboot RPC";
	}
	revision 2016-01-28 {
		description "Add operational state data definitions to support
			     retrieval of software version";
	}
	revision 2015-08-05 {
		description "Initial revision of version 1.";
	}

	container system {
		configd:help "System parameters";

		container state {
			config false;
			description "System operational state";
			container platform {
				configd:get-state "vyatta-system-state-platform";
				description
					"Contains information for identifying the" +
					"system platform.";
				leaf os-name {
					type string;
					description
						"The current platform name.";
				}
				leaf os-release {
					type string;
					description
						"The current release.";
				}
				leaf os-version {
					type string;
					description
						"The current version level.";
				}
			}
		}
	}
	rpc reboot {
		description "Reboot the device";
		input {
			leaf at {
				description "Defer reboot until the specified time";
				type ytypes:date-and-time;
			}
		}
		configd:call-rpc "vyatta-rpc-reboot";
	}
}
