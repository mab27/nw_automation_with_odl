module vyatta-interfaces-dataplane-v1 {
	namespace "urn:vyatta.com:mgmt:vyatta-interfaces-dataplane:1";
	prefix vyatta-interfaces-dataplane-v1;

	import vyatta-interfaces-v1 {
		prefix if;
	}
	import vyatta-types-v1 {
		prefix types;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 Vyatta dataplane interface specific yang file and related
		 template scripts.";

	revision 2016-10-04 {
		description "Pass default IP MTU to script when deleting vif mtu, also remove the validate statement on vif mtu";
	}
	revision 2016-06-10 {
		description "Validate vif mtu is less than physical interface's mtu.";
	}
	revision 2016-04-21 {
		description "Delete dataplane interface address when address node is removed.";
	}
	revision 2016-03-28 {
		description "Remove use of bash in action scripts";
	}
	revision 2015-11-26 {
		description "Modify actions for mac address changes";
	}

	revision 2015-11-23 {
		description "Add definition for dataplane-vifname.";
	}

	revision 2015-11-20 {
		description "Revert to biosdevname naming policy on VMWare.";
	}

	revision 2015-11-10 {
		description "Support for configuring interface CPU affinity.";
	}

	revision 2015-08-14 {
		description "Initial revision of version 1.";
	}

	typedef dataplane-ifname {
		type union {
			// Onboard device
			type string {
				pattern "dp[0-9]+o[0-9]+(d[0-9]+)?";
				configd:pattern-help "<dpFoN>";
			}
			// hotplug slot index
			type string {
				pattern "dp[0-9]+s[0-9]+(f[0-9]+)?(d[0-9]+)?";
				configd:pattern-help "<dpFsN>";
			}
			// PCI device address
			type string {
				pattern "dp[0-9]+(P[0-9]+)?p[0-9]{1,3}s[0-9]{1,3}(f[0-9]+)?(d[0-9]+)?";
				configd:pattern-help "<dpFpNsS>";
			}
			// Biosdevname compatible names. VMware only
			type string {
				pattern "dp[0-9]+p[0-9]+p[0-9]+";
				configd:pattern-help "<dpFpNpS>";
			}
		}
	}

	typedef dataplane-vifname {
		type union {
			// Onboard device
			type string {
				pattern "dp[0-9]+o[0-9]+(d[0-9]+)?\.[1-9][0-9]*";
				configd:pattern-help "<dpFoN.N>";
			}
			// hotplug slot index
			type string {
				pattern "dp[0-9]+s[0-9]+(f[0-9]+)?(d[0-9]+)?\.[1-9][0-9]*";
				configd:pattern-help "<dpFsN.N>";
			}
			// PCI device address
			type string {
				pattern "dp[0-9]+(P[0-9]+)?p[0-9]{1,3}s[0-9]{1,3}(f[0-9]+)?(d[0-9]+)?\.[1-9][0-9]*";
				configd:pattern-help "<dpFpNsS.N>";
			}
			// Biosdevname compatible names. VMware only
			type string {
				pattern "dp[0-9]+p[0-9]+p[0-9]+\.[1-9][0-9]*";
				configd:pattern-help "<dpFpNpS.N>";
			}
		}
	}

	grouping if-parameters {
		leaf description {
			type string;
			configd:help "Interface Description";
			configd:update "ip li set dev $VAR(../@) alias '$VAR(@)'";
			configd:delete "vyatta-interfaces.pl --dev=$VAR(../@) --delete-description";
		}
		uses if:if-parameters-base {
			augment ip {
				leaf disable-forwarding {
					type empty;
					configd:help "Disable IPv4 forwarding on this interface";
					configd:create "sysctl -wq /net/ipv4/conf/$VAR(../../@)/forwarding=0";
					configd:delete "sysctl -wq /net/ipv4/conf/$VAR(../../@)/forwarding=1";
				}
			}
		}
		leaf log_martians {
			type empty;
			configd:help "Enable the logging of bogus packets";
			configd:create "sysctl -wq /net/ipv4/conf/$VAR(../@)/log_martians=1";
			configd:delete "sysctl -wq /net/ipv4/conf/$VAR(../@)/log_martians=0";
		}
	}

	grouping vif-parameters {
		leaf description {
			type string;
			configd:help "Interface Description";
			configd:update "ip li set dev $VAR(../../@).$VAR(../@) alias '$VAR(@)'";
			configd:delete "vyatta-interfaces.pl --dev=$VAR(../../@).$VAR(../@) --delete-description";
		}
		uses if:vif-parameters-base;
	}

	augment /if:interfaces {
		list dataplane {
			configd:priority "318";
			configd:help "Dataplane interface name";
			configd:allowed "vyatta-interfaces.pl --show=dataplane --filter='\.[0-9]+'";
			configd:create "vyatta-interfaces.pl --create-dev $VAR(@)";
			configd:delete "vyatta-interfaces.pl --delete-dev $VAR(@)";
			configd:validate "vyatta-interfaces.pl --validate-interface --dev $VAR(@) --addrs $VAR(./address/@@)";
			configd:end "vyatta-intf-end $VAR(@)";
			key "tagnode";
			leaf tagnode {
				type dataplane-ifname;
				configd:help "Dataplane interface name";
				configd:allowed "vyatta-interfaces.pl --show=dataplane --filter='\.[0-9]+'";
			}
			leaf vlan-protocol {
				type enumeration {
					enum 0x8100;
					enum 0x88A8;
					enum 0x9100;
					enum 0x9200;
					enum 0x9300;
				}
				configd:priority "381";
				configd:help "Vlan Tag Protocol Identifier (default: 0x8100)";
				default "0x8100";
				configd:update "vyatta-interfaces.pl --dev $VAR(../@) --update-vlan-proto $VAR(@)";
				configd:delete "vyatta-interfaces.pl --dev $VAR(../@) --update-vlan-proto 0x8100";
			}
			leaf mtu {
				type uint32 {
					range 68..9000;
				}
				configd:priority "381";
				configd:help "Maximum Transmission Unit (MTU)";
				default "1500";
				configd:validate "vyatta-interfaces.pl --dev $VAR(../@) --validate-dev-mtu $VAR(@) --action ${COMMIT_ACTION}";
				configd:update "vyatta-interfaces.pl --dev $VAR(../@) --set-dev-mtu $VAR(@) --action ${COMMIT_ACTION}";
				configd:delete "vyatta-interfaces.pl --dev $VAR(../@) --set-dev-mtu 1500 --action ${COMMIT_ACTION}";
			}
			uses if-parameters;
			list vif {
				configd:priority "319";
				configd:help "Virtual Interface (VIF) ID";
				configd:create "vyatta-interfaces.pl --dev $VAR(../@) --create-vif $VAR(@)";
				configd:delete "vyatta-interfaces.pl --dev $VAR(../@) --delete-vif $VAR(@)";
				configd:validate "/opt/vyatta/share/tmplscripts/interfaces/dataplane/vif/configd_validate1.cli";
				configd:end "vyatta-intf-end $VAR(../@).$VAR(@)";
				key "tagnode";
				unique "vlan inner-vlan";
				leaf tagnode {
					type uint32 {
						range 1..99999;
					}
					configd:help "Virtual Interface (VIF) ID";
				}
				leaf vlan {
					type uint32 {
						range 1..4094;
					}
					configd:help "Virtual Local Area Network (VLAN) ID";
					configd:update "vyatta-interfaces.pl --dev $VAR(../../@) --update-vif $VAR(../@) --update-vlan";
					configd:delete "vyatta-interfaces.pl --dev $VAR(../../@) --update-vif $VAR(../@) --delete-vlan";
				}
				leaf inner-vlan {
					type uint32 {
						range 1..4094;
					}
					configd:help "Virtual Local Area Network (VLAN) ID";
					configd:update "vyatta-interfaces.pl --dev $VAR(../../@) --update-vif $VAR(../@) --update-ivlan";
					configd:delete "vyatta-interfaces.pl --dev $VAR(../../@) --update-vif $VAR(../@) --del-ivlan";
				}
				leaf disable-link-detect {
					type empty;
					configd:help "Ignore link state changes";
					configd:create "vyatta-link-detect $VAR(../@) off";
					configd:delete "vyatta-link-detect $VAR(../@) on";
				}
				uses vif-parameters;
				leaf mtu {
					type uint32 {
						range 68..9000;
					}
					configd:priority "382";
					configd:help "Maximum Transmission Unit (MTU)";
					configd:update "vyatta-interfaces.pl --dev $VAR(../../@) --update-vif $VAR(../@) --set-mtu $VAR(@)";
					configd:delete "vyatta-interfaces.pl --dev $VAR(../../@) --update-vif $VAR(../@) --del-mtu 1500";
				}
				leaf-list address {
					type if:address-dhcp;
					ordered-by "user";
					configd:help "IP address";
					configd:create "vyatta-address add $VAR(../../@).$VAR(../@) $VAR(@)";
					configd:delete "vyatta-address delete $VAR(../../@).$VAR(../@) $VAR(@)";
					configd:allowed "echo 'dhcp dhcpv6 <>'";
				}
			}
			leaf-list address {
				type if:address-dhcp;
				ordered-by "user";
				configd:help "IP address";
				configd:create "vyatta-address add $VAR(../@) $VAR(@)";
				configd:delete "vyatta-address delete $VAR(../@) $VAR(@)";
				configd:allowed "echo 'dhcp dhcpv6 <>'";
			}
			leaf mac {
				type types:mac-address {
					configd:syntax "/opt/vyatta/share/tmplscripts/interfaces/dataplane/mac/configd_syntax1.cli";
				}
				configd:help "Media Access Control (MAC) address";
				configd:update "vyatta-interfaces.pl --dev $VAR(../@) --set-mac $VAR(@)";
				configd:delete "vyatta-interfaces.pl --dev $VAR(../@) --del-mac";
			}
			leaf cpu-affinity {
				type types:cpu-range;

				configd:help "Interface CPU affinity";
				configd:update "vplane-affinity --dev=$VAR(../@) --set $VAR(@)";
				configd:delete "vplane-affinity --dev=$VAR(../@) --delete";
			}
		}
	}

	augment /if:interfaces/dataplane {
		container hardware {
			presence "Enable hardware binding";
			configd:help "Hardware binding override";
			description "Used to bind an interface to specific PCI hardware";

			must "(count(firmware-index) + count(mac) + count(pci-address) + count(pci-slot) + count(port)) = 1" {
				error-message "Only one of 'firmware-index', 'mac', 'pci-address', 'pci-slot', or 'port' may be set";
			}

			leaf firmware-index {
				type uint32;
				description "Used to match this interface by the ACPI index assigned by the BIOS to an onboard PCI device";
				configd:help "Index assigned by BIOS for onboard device";
			}
			leaf mac {
				type types:mac-address;
				must "not (../mac = '00:00:00:00:00:00') " +
				     "and not (substring(../mac, 2, 1) = '1')" +
				     "and not (substring(../mac, 2, 1) = '3')" +
				     "and not (substring(../mac, 2, 1) = '5')" +
				     "and not (substring(../mac, 2, 1) = '7')" +
				     "and not (substring(../mac, 2, 1) = '9')" +
				     "and not (substring(../mac, 2, 1) = 'b')" +
				     "and not (substring(../mac, 2, 1) = 'd')" +
				     "and not (substring(../mac, 2, 1) = 'f')" {
					error-message "MAC address must not be broadcast or multicast";
				}
				description "Used to match this interface based on the vendor MAC address assigned to a PCI device";
				configd:help "Vendor assigned MAC address";
			}
			leaf pci-address {
				type string {
					pattern "([0-9a-f]{1,4}:)?[0-9a-f]{1,2}:[01]?[0-9a-f].[0-7]" {
						error-message "Must have format as [<domain>:]<bus>:<slot>.<function>, where domain is 0-ffff, bus is 0-ff, slot is 0-1f and function 0-7";
					}
				}
				description "Used to match this interface to a specific PCI device by PCI address";
				configd:help "PCI hardware address";
			}
			leaf pci-slot {
				type uint32;
				description "Used to match this interface to a PCI device in specific PCI slot";
				configd:help "PCI slot";
			}
			leaf port {
				type uint32 {
					range "0..31";
				}
				description "Used to match this interface to a PCI device based on the discovery order used by DPDK";
				configd:help "Discovery order from DPDK";
			}
			leaf pci-function {
				type uint32 {
					range "0..7";
				}
				must "../pci-slot" {
					error-message "pci-function only valid with 'pci-slot'";
				}
				configd:help "Optional qualifier used when a PCI device has multiple functions";
				description "PCI function";
			}
			leaf dev-port {
				type uint32;
				must "../pci-address or ../pci-slot" {
					error-message "dev-port only valid with 'pci-address' or 'pci-slot'";
				}
				configd:help "Optional qualifier used when a PCI device has multiple ports";
				description "Device port on PCI device";
			}
		}
	}
}
