module vyatta-service-dhcp-server-routing-instance-v1 {
	namespace "urn:vyatta.com:mgmt:vyatta-service-dhcp-server-routing-instance:1";
	prefix vyatta-service-dhcp-server-routing-instance-v1;

	import configd-v1 {
		prefix configd;
	}
	import vyatta-service-dhcp-server-v1 {
		prefix server;
	}
	import vyatta-routing-v1 {
		prefix routing;
	}
	import vyatta-interfaces-v1 {
		prefix if;
	}
	import vyatta-interfaces-bridge-v1 {
		prefix if-bridge;
	}
	import vyatta-interfaces-dataplane-v1 {
		prefix if-dataplane;
	}
	import vyatta-interfaces-bonding-v1 {
		prefix if-bonding;
	}
	import vyatta-routing-instance-interfaces-v1 {
		prefix rtintf;
	}

	organization "Brocade Communications Systems, Inc.";
	contact
		"Brocade Communications Systems, Inc.
		 Postal: 130 Holger Way
		         San Jose, CA 95134
		 E-mail: support@Brocade.com
		 Web: www.brocade.com";

	description
		"Copyright (c) 2016-2017 by Brocade Communications Systems, Inc.
		 All rights reserved.

		 The YANG module for vyatta-service-dhcp-server-routing-instance-v1";

	revision 2017-03-01 {
		description "Support getting DHCP server leases via Netconf API";
	}

	revision 2016-06-12 {
		description "Initial revision of version 1.";
	}

	augment /routing:routing/routing:routing-instance/routing:service {
		uses server:dhcp-server-service {
			refine dhcp-server {
				configd:end "/opt/vyatta/share/tmplscripts/service/dhcp-server/configd_vrf_end1.cli";
			}
			refine dhcp-server/listento/interface {
				configd:allowed "vyatta-show-interfaces.pl --vrf=$VAR(../../../../@) --action=dhcp_allowed";
				must "(current() = /if:interfaces/if-dataplane:dataplane/if-dataplane:tagnode)"
					+ "or (substring-after(current(), '.') = /if:interfaces/if-dataplane:dataplane"
					+ "[if-dataplane:tagnode = substring-before(current(), '.')]/if-dataplane:vif/if-dataplane:tagnode)"
					+ "or (current() = /if:interfaces/if-bridge:bridge/if-bridge:tagnode)"
					+ "or (current() = /if:interfaces/if-bonding:bonding/if-bonding:tagnode)"
					+ "or (substring-after(current(), '.') = /if:interfaces/if-bonding:bonding"
					+ "[if-bonding:tagnode = substring-before(current(), '.')]/if-bonding:vif/if-bonding:tagnode)" {
					error-message "Interface name must refer to an existing dataplane, bonding or bridge interface name";
				}
				must "current() = /routing:routing/routing:routing-instance" +
					"[routing:instance-name = current()/../../../../routing:instance-name]" +
					"/rtintf:interface/rtintf:name" {
					error-message "Interface must be configured in this routing instance";
				}
			}
			refine dhcp-server/state {
				configd:get-state "/opt/vyatta/bin/dhcp-show-leases.pl --rtinst all --netconf";
			}
		}
	}
}
