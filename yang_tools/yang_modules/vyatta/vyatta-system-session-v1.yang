module vyatta-system-session-v1 {
	namespace "urn:vyatta.com:mgmt:vyatta-system-session:1";
	prefix vyatta-system-session-v1;

	import vyatta-system-v1 {
		prefix system;
	}
	import configd-v1 {
		prefix configd;
	}
	import vyatta-fw-types-v1 {
		prefix fw-types;
	}
	import vyatta-npf-v1 {
		prefix npf;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 YANG module and scripts for Vyatta firewall session
		 configuration and operation";

	revision 2016-08-09 {
		description "Add descriptions to many nodes.
			     Update custom handling to use common types.
			     Move scripts from under tmplscripts.";
	}
	revision 2016-04-15 {
		description "Add VRF support.";
	}
	revision 2015-08-06 {
		description "Initial revision.";
	}

	typedef timeout {
		type uint32 {
			range 1..21474836;
		}
	}

	grouping timeout-group {
		container timeout {
			presence "timeout configuration";
			description "Connection timeout options";
			configd:help "Connection timeout options";
			container tcp {
				presence "timeout configuration";
				description "TCP connection timeout options";
				configd:help "TCP connection timeout options";
				leaf close-wait {
					type timeout;
					description "TCP CLOSE-WAIT timeout in seconds";
					configd:help "TCP CLOSE-WAIT timeout in seconds";
					configd:delete "vyatta-dp-npf-timeouts.pl --cmd=delete --proto=tcp --state=close-wait --timeout=21600 --vrf=$VAR(../../../../../../routing-instance/@)";
					configd:update "vyatta-dp-npf-timeouts.pl --cmd=update --proto=tcp --state=close-wait --timeout=$VAR(@) --vrf=$VAR(../../../../../../routing-instance/@)";
				}
				leaf established {
					type timeout;
					description "TCP ESTABLISHED timeout in seconds";
					configd:help "TCP ESTABLISHED timeout in seconds";
					configd:delete "vyatta-dp-npf-timeouts.pl --cmd=delete --proto=tcp --state=established --timeout=86400 --vrf=$VAR(../../../../../../routing-instance/@)";
					configd:update "vyatta-dp-npf-timeouts.pl --cmd=update --proto=tcp --state=established --timeout=$VAR(@) --vrf=$VAR(../../../../../../routing-instance/@)";
				}
				leaf syn-sent {
					type timeout;
					description "TCP SYN-SENT timeout in seconds";
					configd:help "TCP SYN-SENT timeout in seconds";
					configd:delete "vyatta-dp-npf-timeouts.pl --cmd=delete --proto=tcp --state=syn-sent --timeout=30 --vrf=$VAR(../../../../../../routing-instance/@)";
					configd:update "vyatta-dp-npf-timeouts.pl --cmd=update --proto=tcp --state=syn-sent --timeout=$VAR(@) --vrf=$VAR(../../../../../../routing-instance/@)";
				}
				leaf fin-received {
					type timeout;
					description "TCP FIN-RECEIVED timeout in seconds";
					configd:help "TCP FIN-RECEIVED timeout in seconds";
					configd:delete "vyatta-dp-npf-timeouts.pl --cmd=delete --proto=tcp --state=fin-received --timeout=240 --vrf=$VAR(../../../../../../routing-instance/@)";
					configd:update "vyatta-dp-npf-timeouts.pl --cmd=update --proto=tcp --state=fin-received --timeout=$VAR(@) --vrf=$VAR(../../../../../../routing-instance/@)";
				}
				leaf fin-sent {
					type timeout;
					description "TCP FIN-SENT timeout in seconds";
					configd:help "TCP FIN-SENT timeout in seconds";
					configd:delete "vyatta-dp-npf-timeouts.pl --cmd=delete --proto=tcp --state=fin-sent --timeout=240 --vrf=$VAR(../../../../../../routing-instance/@)";
					configd:update "vyatta-dp-npf-timeouts.pl --cmd=update --proto=tcp --state=fin-sent --timeout=$VAR(@) --vrf=$VAR(../../../../../../routing-instance/@)";
				}
				leaf closing {
					type timeout;
					description "TCP CLOSING timeout in seconds";
					configd:help "TCP CLOSING timeout in seconds";
					configd:delete "vyatta-dp-npf-timeouts.pl --cmd=delete --proto=tcp --state=closing --timeout=30 --vrf=$VAR(../../../../../../routing-instance/@)";
					configd:update "vyatta-dp-npf-timeouts.pl --cmd=update --proto=tcp --state=closing --timeout=$VAR(@) --vrf=$VAR(../../../../../../routing-instance/@)";
				}
				leaf simsyn-sent {
					type timeout;
					description "TCP SIMSYN-SENT timeout in seconds";
					configd:help "TCP SIMSYN-SENT timeout in seconds";
					configd:delete "vyatta-dp-npf-timeouts.pl --cmd=delete --proto=tcp --state=simsyn-sent --timeout=30 --vrf=$VAR(../../../../../../routing-instance/@)";
					configd:update "vyatta-dp-npf-timeouts.pl --cmd=update --proto=tcp --state=simsyn-sent --timeout=$VAR(@) --vrf=$VAR(../../../../../../routing-instance/@)";
				}
				leaf time-wait {
					type timeout;
					description "TCP TIME-WAIT timeout in seconds";
					configd:help "TCP TIME-WAIT timeout in seconds";
					configd:delete "vyatta-dp-npf-timeouts.pl --cmd=delete --proto=tcp --state=time-wait --timeout=240 --vrf=$VAR(../../../../../../routing-instance/@)";
					configd:update "vyatta-dp-npf-timeouts.pl --cmd=update --proto=tcp --state=time-wait --timeout=$VAR(@) --vrf=$VAR(../../../../../../routing-instance/@)";
				}
				leaf last-ack {
					type timeout;
					description "TCP LAST-ACK timeout in seconds";
					configd:help "TCP LAST-ACK timeout in seconds";
					configd:delete "vyatta-dp-npf-timeouts.pl --cmd=delete --proto=tcp --state=last-ack --timeout=30 --vrf=$VAR(../../../../../../routing-instance/@)";
					configd:update "vyatta-dp-npf-timeouts.pl --cmd=update --proto=tcp --state=last-ack --timeout=$VAR(@) --vrf=$VAR(../../../../../../routing-instance/@)";
				}
				leaf syn-received {
					type timeout;
					description "TCP SYN-RECEIVED timeout in seconds";
					configd:help "TCP SYN-RECEIVED timeout in seconds";
					configd:delete "vyatta-dp-npf-timeouts.pl --cmd=delete --proto=tcp --state=syn-received --timeout=60 --vrf=$VAR(../../../../../../routing-instance/@)";
					configd:update "vyatta-dp-npf-timeouts.pl --cmd=update --proto=tcp --state=syn-received --timeout=$VAR(@) --vrf=$VAR(../../../../../../routing-instance/@)";
				}
				leaf closed {
					type timeout;
					description "TCP CLOSED timeout in seconds";
					configd:help "TCP CLOSED timeout in seconds";
					configd:delete "vyatta-dp-npf-timeouts.pl --cmd=delete --proto=tcp --state=closed --timeout=10 --vrf=$VAR(../../../../../../routing-instance/@)";
					configd:update "vyatta-dp-npf-timeouts.pl --cmd=update --proto=tcp --state=closed --timeout=$VAR(@) --vrf=$VAR(../../../../../../routing-instance/@)";
				}
				leaf fin-wait {
					type timeout;
					description "TCP FIN-WAIT timeout in seconds";
					configd:help "TCP FIN-WAIT timeout in seconds";
					configd:delete "vyatta-dp-npf-timeouts.pl --cmd=delete --proto=tcp --state=fin-wait --timeout=21600 --vrf=$VAR(../../../../../../routing-instance/@)";
					configd:update "vyatta-dp-npf-timeouts.pl --cmd=update --proto=tcp --state=fin-wait --timeout=$VAR(@) --vrf=$VAR(../../../../../../routing-instance/@)";
				}
			}
			container icmp {
				presence "timeout configuration";
				description "ICMP timeout";
				configd:help "ICMP timeout";
				leaf established {
					type timeout;
					description "ICMP ESTABLISHED timeout in seconds";
					configd:help "ICMP ESTABLISHED timeout in seconds";
					configd:delete "vyatta-dp-npf-timeouts.pl --cmd=delete --proto=icmp --state=established --timeout=60 --vrf=$VAR(../../../../../../routing-instance/@)";
					configd:update "vyatta-dp-npf-timeouts.pl --cmd=update --proto=icmp --state=established --timeout=$VAR(@) --vrf=$VAR(../../../../../../routing-instance/@)";
				}
				leaf new {
					type timeout;
					description "ICMP NEW timeout in seconds";
					configd:help "ICMP NEW timeout in seconds";
					configd:delete "vyatta-dp-npf-timeouts.pl --cmd=delete --proto=icmp --state=new --timeout=30 --vrf=$VAR(../../../../../../routing-instance/@)";
					configd:update "vyatta-dp-npf-timeouts.pl --cmd=update --proto=icmp --state=new --timeout=$VAR(@) --vrf=$VAR(../../../../../../routing-instance/@)";
				}
			}
			container other {
				presence "timeout configuration";
				description "Generic connection timeout";
				configd:help "Generic connection timeout";
				leaf established {
					type timeout;
					description "Generic ESTABLISHED timeout in seconds";
					configd:help "Generic ESTABLISHED timeout in seconds";
					configd:delete "vyatta-dp-npf-timeouts.pl --cmd=delete --proto=other --state=established --timeout=60 --vrf=$VAR(../../../../../../routing-instance/@)";
					configd:update "vyatta-dp-npf-timeouts.pl --cmd=update --proto=other --state=established --timeout=$VAR(@) --vrf=$VAR(../../../../../../routing-instance/@)";
				}
				leaf new {
					type timeout;
					description "Generic NEW timeout in seconds";
					configd:help "Generic NEW timeout in seconds";
					configd:delete "vyatta-dp-npf-timeouts.pl --cmd=delete --proto=other --state=new --timeout=30 --vrf=$VAR(../../../../../../routing-instance/@)";
					configd:update "vyatta-dp-npf-timeouts.pl --cmd=update --proto=other --state=new --timeout=$VAR(@) --vrf=$VAR(../../../../../../routing-instance/@)";
				}
			}
			container custom {
				presence "timeout configuration";
				description "Custom connection timeout options";
				configd:help "Custom connection timeout options";
				configd:validate "validate-fw-groups --variant=custom-timeout --vrf=$VAR(../../../../../routing-instance/@)";
				list rule {
					description "Rule number";
					configd:help "Rule number";
					configd:end "end-custom-timeout";
					key "tagnode";
					leaf tagnode {
						type fw-types:rule-number;
					}
					leaf expire {
						type timeout;
						mandatory "true";
						description "Expire time out value for this rule";
						configd:help "Expire time out value for this rule";
					}
					container source {
						presence "timeout configuration";
						description "Source parameters";
						configd:help "Source parameters";
						uses npf:rule-ip-address-custom;
						uses npf:rule-port;
					}
					container destination {
						presence "timeout configuration";
						description "Destination parameters";
						configd:help "Destination parameters";
						uses npf:rule-ip-address-custom;
						uses npf:rule-port;
					}
					uses npf:rule-protocol;
				}
			}
			container udp {
				presence "timeout configuration";
				description "UDP timeout";
				configd:help "UDP timeout";
				leaf established {
					type timeout;
					description "UDP ESTABLISHED timeout in seconds";
					configd:help "UDP ESTABLISHED timeout in seconds";
					configd:delete "vyatta-dp-npf-timeouts.pl --cmd=delete --proto=udp --state=established --timeout=60 --vrf=$VAR(../../../../../../routing-instance/@)";
					configd:update "vyatta-dp-npf-timeouts.pl --cmd=update --proto=udp --state=established --timeout=$VAR(@) --vrf=$VAR(../../../../../../routing-instance/@)";
				}
				leaf new {
					type timeout;
					description "UDP NEW timeout in seconds";
					configd:help "UDP NEW timeout in seconds";
					configd:delete "vyatta-dp-npf-timeouts.pl --cmd=delete --proto=udp --state=new --timeout=30 --vrf=$VAR(../../../../../../routing-instance/@)";
					configd:update "vyatta-dp-npf-timeouts.pl --cmd=update --proto=udp --state=new --timeout=$VAR(@) --vrf=$VAR(../../../../../../routing-instance/@)";
				}
			}
		}
	}

	augment /system:system {
		container session {
			presence "timeout configuration";
			description "Configure timeouts for session";
			configd:help "Configure timeouts for session";
			leaf table-size {
				type uint32 {
					range 1..100000000;
				}
				description "Size of connection tracking table";
				configd:help "Size of connection tracking table";
				default "1048576";
				configd:update "vyatta-dp-npf.pl --variant=firewall --cmd=update-global-table-size";
			}
			uses timeout-group;
		}
	}
}
