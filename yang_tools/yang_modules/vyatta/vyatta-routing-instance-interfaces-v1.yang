module vyatta-routing-instance-interfaces-v1 {
        namespace "urn:vyatta.com:mgmt:vyatta-routing-instance-interfaces-v1:1";
        prefix vyatta-routing-instance-if-v1;

	import configd-v1 { prefix configd; }
	import vyatta-routing-v1 { prefix vyatta-routing; }
	import vyatta-types-v1 {
		prefix types;
	}

	organization "Brocade Communications Systems, Inc.";
	contact
		"Brocade Communications Systems, Inc.
		Postal: 130 Holger Way
			San Jose, CA 95134
		E-mail: support@Brocade.com
		Web: www.brocade.com";

	description
		"Copyright (c) 2016 by Brocade Communications Systems, Inc.
		 All rights reserved.

		 The YANG module for vyatta-routing-instance-interfaces-v1";

	revision 2016-08-12 {
		description "Add warning for undefined interfaces.";
	}

	revision 2016-04-11 {
		description "Initial revision of version 1.";
	}

	augment /vyatta-routing:routing {
		configd:begin "/opt/vyatta/sbin/vrf-bind-interface --all";
	}

	augment /vyatta-routing:routing/vyatta-routing:routing-instance {
		list interface {
			description "List of interfaces to bind with this routing-instance";
			configd:help "Bind interface to routing-instance";
			key "name";
			leaf "name" {
				type types:interface-ifname;
				configd:allowed "/opt/vyatta/sbin/vyatta-interfaces.pl --show all";
				configd:validate "/opt/vyatta/share/tmplscripts/routing-instance/routing-instance-validate.sh";

				must "not(current() = 'lo') and " +
					"(not(starts-with(current(),'lord')))" {
					error-message "Loopback interface name lo or name starts with lord can't be bound to routing-instances.";
				}
				must "(1 = count(../../../vyatta-routing:routing-instance/interface[name = current()]))" {
					error-message "Interface cannot be bound to multiple routing instances";
				}
			}
		}
	}
}
