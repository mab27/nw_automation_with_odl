module vyatta-policy-pbr-dpi-v1 {
	namespace "urn:vyatta.com:mgmt:vyatta-policy-pbr-dpi:1";
	prefix vyatta-policy-pbr-dpi-v1;

	import vyatta-policy-v1 {
		prefix policy;
	}
	import vyatta-policy-route-v1 {
		prefix policy-route;
	}
	import vyatta-policy-pbr-v1 {
		prefix pbr;
	}
	import vyatta-dpi-v1 {
		prefix dpi;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 YANG module for PBR DPI.";

	revision 2016-07-14 {
		description "Initial revision.";
	}

	augment /policy:policy/policy-route:route/pbr:pbr/pbr:rule {
		description "Add DPI functionality to PBR rule";
		uses dpi:dpi;
	}
}
