module vyatta-service-ssh-routing-instance-v1 {
	namespace "urn:vyatta.com:mgmt:vyatta-service-ssh-routing-instance:1";
	prefix vyatta-service-ssh-routing-instance-v1;

	import vyatta-service-ssh-v1 {
		prefix ssh-service;
	}
	import configd-v1 {
		prefix configd;
	}
	import vyatta-routing-v1 {
		prefix rt-instance;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 routing-instance SSH configuration";

	revision 2016-04-13 {
		description "Initial revision of version 1.";
	}

	augment /rt-instance:routing/rt-instance:routing-instance/rt-instance:service {
		uses ssh-service:service-ssh {
			refine ssh {
				configd:help "This sets the config options for sshd on the current routing-instance.";
				configd:delete "/opt/vyatta/share/tmplscripts/service/ssh/configd_update --routing-instance=$VAR(../../@) --action=delete";
				configd:update "/opt/vyatta/share/tmplscripts/service/ssh/configd_update --routing-instance=$VAR(../../@) --action=update";
			}
		}
	}
}
