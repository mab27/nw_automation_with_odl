module vyatta-system-package-v1 {
	namespace "urn:vyatta.com:mgmt:vyatta-system-package:1";
	prefix vyatta-system-package-v1;

	import vyatta-types-v1 {
		prefix types;
	}
	import vyatta-system-v1 {
		prefix system;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 Package management configuration";

	revision 2016-08-03 {
		description "Change archive source creation";
	}
	revision 2016-03-15 {
		description "Add sources repository (via deb-src) too";
	}
	revision 2015-08-14 {
		description "Initial revision of version 1.";
	}

	augment /system:system {
		container package {
			presence "true";
			configd:priority "400";
			configd:help "Package update repository parameters";
			leaf auto-sync {
				type uint32 {
					range 0..31 {
						error-message "auto-sync must be between 0 and 32 days";
					}
				}
				default "1";
				configd:help "Update the the repository cache every n days (0 disables auto-update)";
				configd:update "/opt/vyatta/share/tmplscripts/system/package/auto-sync/configd_update1.cli";
				configd:delete "/opt/vyatta/share/tmplscripts/system/package/auto-sync/configd_delete1.cli";
			}
			list repository {
				configd:help "Debian archive name";
				configd:end "setup-package-repo --archive=$VAR(@)";
				configd:validate "/opt/vyatta/share/tmplscripts/system/package/repository/configd_validate1.cli";
				configd:validate "/opt/vyatta/share/tmplscripts/system/package/repository/configd_validate2.cli";
				key "archive";
				leaf archive {		
					type types:alpha-numeric {
						configd:help "Debian archive name";
					}
				}
				leaf description {
					type string;
					configd:help "Repository description";
				}
				leaf password {
					type string {
						pattern "[^!]*" {
							error-message "Do not use '!' in url";
						}
					}
					configd:secret "true";
					configd:help "Repository password";
					default "";
				}
				leaf username {
					type string {
						pattern "[^!]*" {
							error-message "Do not use '!' in url";
						}
					}
					configd:help "Repository username";
					default "";
				}
				leaf url {
					type string {
						pattern "[^!]+" {
							error-message "URL must not be null and must not contain '!'";
						}
					}
					configd:help "Repository URL";
				}
				leaf components {
					type string {
						pattern "[^!]+" {
							error-message "Do not use '!' in component name";
						}
					}
					configd:help "Repository component names";
				}
				leaf distribution {
					type string {
						pattern "[^!]+" {
							error-message "Do not use '!' in distribution name";
						}
					}
					configd:help "Distribution name";
				}
				leaf sources {
					type empty;
					configd:help "Add sources repository (via deb-src) too";
					description "Add sources repository (via deb-src) too";
				}
			}
		}
	}
}
