module vyatta-system-time-routing-instance-v1 {
	namespace "urn:vyatta.com:mgmt:vyatta-system-time-routing-instance:1";
	prefix vyatta-system-time-routing-instance-v1;

	import vyatta-system-v1 {
		prefix system;
	}
	import vyatta-system-time-v1 {
		prefix time;
	}
	import vyatta-routing-v1 {
		prefix rt-instance;
	}
	import configd-v1 {
		prefix configd;
	}
	organization "Brocade Communications Systems, Inc.";
	contact
		"Brocade Communications Systems, Inc.
		 Postal: 130 Holger Way
		         San Jose, CA 95134
		 E-mail: support@Brocade.com
		 Web: www.brocade.com";

	description
		"Copyright (c) 2016-2017 by Brocade Communications Systems, Inc.
		 All rights reserved.

		 VRF NTP configuration";

	revision 2017-01-31 {
		description "Rework YANG nodeset != comparisons.";
	}

	revision 2016-06-16 {
		description "Initial revision of version 1.";
	}

	augment /rt-instance:routing/rt-instance:routing-instance/rt-instance:system {
		uses time:system-time-ntp {
			refine ntp {
				configd:create "/opt/vyatta/sbin/vyatta_configure_ntp.pl --operation=start --rtinstance=$VAR(../../@)";
				configd:delete "/opt/vyatta/sbin/vyatta_configure_ntp.pl --operation=stop --rtinstance=$VAR(../../@)";
				configd:update "/opt/vyatta/sbin/vyatta_configure_ntp.pl --operation=restart --rtinstance=$VAR(../../@)";
				must "count(/system:system/time:ntp/time:server) = 0" {
					error-message "Cannot also configure NTP in default routing-instance";
				}
				must "count(/rt-instance:routing/rt-instance:routing-instance[not(rt-instance:instance-name ="
				+ "current()/../../rt-instance:instance-name)]/rt-instance:system/ntp) = 0" {
					error-message "Cannot configure NTP in more than one routing-instance simultaneously";
				}
			}
		}
	}

}
