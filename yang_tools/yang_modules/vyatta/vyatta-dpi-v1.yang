module vyatta-dpi-v1 {
	namespace "urn:vyatta.com:mgmt:vyatta-dpi:1";
	prefix vyatta-dpi-v1;

	import configd-v1 {
		prefix configd;
	}

	organization "Brocade Communications Systems, Inc.";
	contact
		"Brocade Communications Systems, Inc.
		 Postal: 130 Holger Way
			 San Jose, CA 95134
		 E-mail: support@Brocade.com
		 Web: www.brocade.com";

	description
		"Copyright (c) 2016-2017 by Brocade Communications Systems, Inc.
		 All rights reserved.

		 YANG module for Deep Packet Inspection (DPI)";

	revision 2017-03-03 {
		description "Make groupings for name and type (leaf) and add
			     protocol and type (list) groupings.";
	}
	revision 2016-07-14 {
		description "Initial revision.";
	}

	grouping dpi-name {
		list name {
			description "Specify an application by name";
			configd:help "Match by application name";
			configd:allowed "dpi --list-app-names";
			configd:validate "dpi --validate-app-name $VAR(@)";
			max-elements 1;

			key name;
			leaf name {
				type string;
			}
		}
	}

	grouping dpi-protocol {
		list protocol {
			description "Specify an application by protocol";
			configd:help "Match by application protocol";
			configd:allowed "dpi --list-app-names";
			configd:validate "dpi --validate-app-name $VAR(@)";
			max-elements 1;

			key protocol;
			leaf protocol {
				type string;
			}
		}
	}

	grouping dpi-type-leaf {
		leaf type {
			description "Specify an application by type";
			configd:help "Match by application type";
			configd:allowed "dpi --list-app-types";
			configd:validate "dpi --validate-app-type $VAR(@)";
			type string;
		}
	}

	grouping dpi-type {
		list type {
			description "Specify an application by type";
			configd:help "Match by application type";
			configd:allowed "dpi --list-app-types";
			configd:validate "dpi --validate-app-type $VAR(@)";
			max-elements 1;

			key type;
			leaf type {
				type string;
			}
		}
	}

	grouping dpi {
		container application {
			must "not(*) or (count(name|type) <= 1)" {
				error-message "Specify either the application name or the application type, not both";
			}
			description
				"Specify applications to match.
				 Applications can be specified by name or by type";
			configd:help "Match applications";
			uses dpi-name;
			uses dpi-type-leaf;
		}
	}
}
