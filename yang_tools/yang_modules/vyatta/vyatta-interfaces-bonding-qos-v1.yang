module vyatta-interfaces-bonding-qos-v1 {
	namespace "urn:vyatta.com:mgmt:vyatta-interfaces-bonding-qos:1";
	prefix vyatta-interfaces-bonding-qos-v1;

	import configd-v1 {
		prefix configd;
	}
	import vyatta-interfaces-v1 {
		prefix if;
	}
	import vyatta-policy-v1 {
		prefix policy;
	}
	import vyatta-policy-qos-v1 {
		prefix qos;
	}
	import vyatta-interfaces-policy-v1 {
		prefix interfaces-policy;
	}
	import vyatta-interfaces-bonding-v1 {
		prefix interfaces-bonding;
	}

	organization "Brocade Communications Systems, Inc.";

	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-interfaces-bonding-qos-v1";

	revision 2016-04-27 {
		description "Initial revision";
	}

	grouping qos-bonding {
		leaf qos {
			type leafref {
				path "/policy:policy/qos:qos/qos:name/qos:id";
			}
			configd:help "QoS policy for interface";
		}
	}

	augment /if:interfaces/interfaces-bonding:bonding {
		configd:begin "/opt/vyatta/share/tmplscripts/interfaces/bonding/policy/qos/configd_begin.sh";
		configd:end "/opt/vyatta/share/tmplscripts/interfaces/bonding/policy/qos/configd_end.sh";
	}

	augment /if:interfaces/interfaces-bonding:bonding/interfaces-policy:policy {
		uses qos-bonding;
	}

	augment /if:interfaces/interfaces-bonding:bonding/interfaces-bonding:vif/interfaces-policy:policy {
		uses qos-bonding;
	}
}
