module vyatta-system-syslog-routing-instance-v1 {
	namespace "urn:vyatta.com:mgmt:vyatta-system-syslog-routing-instance:1";
	prefix vyatta-system-syslog-routing-instance-v1;

	import vyatta-system-syslog-v1 {
		prefix syslog;
	}
	import vyatta-routing-v1 {
		prefix routing;
	}

	organization "Brocade Communications Systems, Inc.";
	contact
		"Brocade Communications Systems, Inc.
		 Postal: 130 Holger Way
		         San Jose, CA 95134
		 E-mail: support@Brocade.com
		 Web: www.brocade.com";
        
	description
		"Copyright (c) 2016 by Brocade Communications Systems, Inc.
		 All rights reserved.

		 Syslog VRF configuration";

	revision 2016-04-22 {
		description "Initial revision";
	}

	augment /routing:routing/routing:routing-instance/routing:system {
		uses syslog:syslog-base;
	}

	augment /routing:routing/routing:routing-instance/routing:system/syslog {
		uses syslog:syslog-remote;
	}	

}
