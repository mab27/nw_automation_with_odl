module vyatta-protocols-bfd-routing-instance-v1 {
	namespace "urn:vyatta.com:mgmt:vyatta-protocols-bfd-routing-instance:1";
	prefix vyatta-protocols-bfd-routing-instance-v1;

	import configd-v1 {
		prefix configd;
	}
 	import vyatta-routing-v1 {
		prefix vyatta-routing;
	}
	import vyatta-protocols-bfd-v1 {
		prefix protocols-bfd;
	}
	import vyatta-protocols-static-routing-instance-v1 {
		prefix routing-instance-static;
	}
	import vyatta-protocols-ospf-routing-instance-v1 {
		prefix routing-instance-ospf;
	}
	import vyatta-protocols-ospfv3-routing-instance-v1 {
		prefix routing-instance-ospfv3;
	}
	import vyatta-protocols-bgp-routing-instance-v1 {
		prefix routing-instance-bgp;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for vyatta-protocols-bfd-routing-instance-v1";

	revision 2016-05-10 {
		description "Initial revision of version 1 :
		1. Introduced routing-instance (VRF) support for bfd over ipv6 static route.
		2. Introducing support for enabling/disabling BFD logs independently on each routing-instance.";
	}

	augment /vyatta-routing:routing/vyatta-routing:routing-instance/vyatta-routing:protocols/routing-instance-static:static/routing-instance-static:route/routing-instance-static:next-hop {
		uses protocols-bfd:enable-fall-over-bfd;
	}

	augment /vyatta-routing:routing/vyatta-routing:routing-instance/vyatta-routing:protocols {
		container bfd {
			uses protocols-bfd:session-template;
			uses protocols-bfd:bfd-logging;
		}
	}

	augment /vyatta-routing:routing/vyatta-routing:routing-instance/vyatta-routing:protocols/routing-instance-static:static/routing-instance-static:route6/routing-instance-static:next-hop {
		uses protocols-bfd:enable-fall-over-bfd;
	}

	augment /vyatta-routing:routing/vyatta-routing:routing-instance/vyatta-routing:protocols/routing-instance-bgp:bgp/routing-instance-bgp:neighbor {
		uses protocols-bfd:enable-fall-over-bfd;
	}

	augment /vyatta-routing:routing/vyatta-routing:routing-instance/vyatta-routing:protocols/routing-instance-ospf:ospf/routing-instance-ospf:process/routing-instance-ospf:area/routing-instance-ospf:virtual-link {
		uses protocols-bfd:enable-fall-over-bfd {
			refine fall-over/bfd {
				configd:create "/opt/vyatta/share/tmplscripts/protocols/all/fall-over/bfd/configd_create.sh";
				configd:delete "/opt/vyatta/share/tmplscripts/protocols/all/fall-over/bfd/configd_delete.sh";
			}
		}
	}

	augment /vyatta-routing:routing/vyatta-routing:routing-instance/vyatta-routing:protocols/routing-instance-ospfv3:ospfv3/routing-instance-ospfv3:process/routing-instance-ospfv3:area/routing-instance-ospfv3:virtual-link {
		uses protocols-bfd:enable-fall-over-bfd {
			refine fall-over/bfd {
				configd:create "/opt/vyatta/share/tmplscripts/protocols/all/fall-over/bfd/configd_create.sh";
				configd:delete "/opt/vyatta/share/tmplscripts/protocols/all/fall-over/bfd/configd_delete.sh";
			}
		}
	}
}
