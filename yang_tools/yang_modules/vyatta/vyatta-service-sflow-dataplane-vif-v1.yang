module vyatta-service-sflow-dataplane-vif-v1 {
	namespace "urn:vyatta.com:mgmt:vyatta-service-sflow-dataplane-vif:1";
	prefix vyatta-service-sflow-dataplane-vif-v1;

	import configd-v1 {
		prefix configd;
	}
	import vyatta-interfaces-v1 {
		prefix if;
	}
	import vyatta-interfaces-dataplane-v1 {
		prefix if-dp;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-service-sflow-dataplane-vif-v1";

	revision 2016-04-28 {
		description "Add sFlow support on dataplane VIF";
	}

	augment /if:interfaces/if-dp:dataplane/if-dp:vif {
		leaf sflow {
			type empty;
			configd:priority "911";
			configd:help "Enable/Disable sflow for interface";
			configd:delete "vplane-sflow.pl --cmd=disable --intf=$VAR(../../@) --type=$VAR(../..) --vif=$VAR(../@)";
			configd:update "vplane-sflow.pl --cmd=enable --intf=$VAR(../../@) --type=$VAR(../..) --vif=$VAR(../@)";
		}
	}
}
