module vyatta-service-lldp-v1 {
	namespace "urn:vyatta.com:mgmt:vyatta-service-lldp:1";
	prefix vyatta-service-lldp-v1;

	import vyatta-types-v1 {
		prefix types;
	}
	import vyatta-services-v1 {
		prefix service;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module for vyatta-service-lldp-v1";

	revision 2015-08-06 {
		description "Initial revision of version 1.";
	}

	augment /service:service {
		container lldp {
			presence "true";
			configd:help "LLDP settings";
			configd:priority "985";
			configd:end "/opt/vyatta/share/tmplscripts/service/lldp/configd_end.sh";
			leaf management-address {
				type types:ipv4-address;
				configd:help "IPv4 management address";
			}
			container legacy-protocols {
				presence "true";
				configd:help "Legacy (vendor specific) protocols";
				leaf cdp {
					type empty;
					configd:help "Listen for CDP for Cisco routers/switches";
				}
				leaf fdp {
					type empty;
					configd:help "Listen for FDP for Foundry routers/switches";
				}
				leaf edp {
					type empty;
					configd:help "Listen for EDP for Extreme routers/switches";
				}
				leaf sonmp {
					type empty;
					configd:help "Listen for SONMP for Nortel routers/switches";
				}
			}
			list interface {
				configd:help "Location data for interface";
				configd:allowed "/opt/vyatta/share/tmplscripts/service/lldp/interface/configd_allowed.sh";
				key "tagnode";
				leaf tagnode {
					type string;
					configd:help "Location data for interface";
					configd:allowed "/opt/vyatta/share/tmplscripts/service/lldp/interface/configd_allowed.sh";
				}
				leaf disable {
					type empty;
					configd:help "Disable lldp on this interface";
				}
				container location {
					presence "true";
					configd:help "LLDP-MED location data [REQUIRED]";
					leaf elin {
						type string {
							pattern '[0-9]{10,25}' {
								error-message "ELIN number must be between 10-25 numbers.";
							}
						}
						configd:help "ECS ELIN number";
						configd:validate "/opt/vyatta/share/tmplscripts/service/lldp/interface/location/elin/configd_validate1.cli";
						configd:validate "/opt/vyatta/share/tmplscripts/service/lldp/interface/location/elin/configd_validate2.cli";
					}
					container coordinate-based {
						presence "true";
						configd:help "Coordinate based location";
						configd:validate "/opt/vyatta/share/tmplscripts/service/lldp/interface/location/coordinate-based/configd_validate1.cli";
						configd:validate "/opt/vyatta/share/tmplscripts/service/lldp/interface/location/coordinate-based/configd_validate2.cli";
						configd:validate "/opt/vyatta/share/tmplscripts/service/lldp/interface/location/coordinate-based/configd_validate3.cli";
						configd:validate "/opt/vyatta/share/tmplscripts/service/lldp/interface/location/coordinate-based/configd_validate4.cli";
						leaf latitude {
							type string {
								pattern '[-\+0-9\.]+[nNsS]' {
									error-message "Invalid latitude.";
								}
							}
							configd:help "Latitude [REQUIRED]";
						}
						leaf datum {
							type enumeration {
								enum "WGS84";
								enum "NAD83";
								enum "MLLW";
							}
							configd:help "Coordinate datum type";
							default "WGS84";
						}
						leaf longitude {
							type string {
								pattern '[-\+0-9\.]+[eEwW]' {
									error-message "Invalid longitude.";
								}
							}
							configd:help "Longitude [REQUIRED]";
						}
						leaf altitude {
							type string {
								pattern '[-\+0-9\.]+' {
									error-message "Invalid altitude.";
								}
							}
							configd:help "Altitude in meters";
						}
					}
					container civic-based {
						presence "true";
						configd:help "Civic-based location data";
						configd:validate "/opt/vyatta/share/tmplscripts/service/lldp/interface/location/civic-based/configd_validate1.cli";
						configd:validate "/opt/vyatta/share/tmplscripts/service/lldp/interface/location/civic-based/configd_validate2.cli";
						configd:validate "/opt/vyatta/share/tmplscripts/service/lldp/interface/location/civic-based/configd_validate3.cli";
						leaf country-code {
							type string {
								pattern '[A-Za-z]{2}' {
									error-message "country-code must be 2 characters.";
								}
							}
							configd:help "Country code [REQUIRED]";
						}
						list ca-type {
							configd:help "LLDP-MED Civic Address type [REQUIRED]";
							configd:validate "/opt/vyatta/share/tmplscripts/service/lldp/interface/location/civic-based/ca-type/configd_validate1.cli";
							key "tagnode";
							leaf tagnode {
								type uint32 {
									range 0..128 {
										error-message "ca-type must between 0-128.";
									}
								}
								configd:help "LLDP-MED Civic Address type [REQUIRED]";
							}
							leaf ca-value {
								type string {
									pattern '[A-Za-z0-9 \-_\.,]{0,255}' {
										error-message "ca-value must be less than 256 characters.";
									}
								}
								configd:help "Civic address value for ca-type [REQUIRED]";
							}
						}
					}
				}
			}
			container snmp {
				presence "true";
				configd:help "SNMP parameters for LLDP";
				leaf enable {
					type empty;
					configd:help "Enable SNMP queries of the LLDP database";
				}
			}
		}
	}
}
