module vyatta-protocols-msdp-routing-instance-v1 {
	namespace "urn:vyatta.com:mgmt:vyatta-protocols-msdp-routing-instance:1";
	prefix vyatta-protocols-msdp-routing-instancev1;

	import configd-v1 {
		prefix configd;
	}
	import vyatta-routing-v1 {
		prefix routing;
	}
	import vyatta-protocols-msdp-v1 {
		prefix msdp;
	}
	
	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-protocols-msdp-routing-instance-v1";

	revision 2016-04-25 {
		description "Augment /routing/routing-instance/protocols";
	}

	augment /routing:routing/routing:routing-instance/routing:protocols {
		uses msdp:msdp-parameters {
			refine msdp {
				configd:validate "vyatta-msdp-validate --routing-instance $VAR(../../@)";
				configd:end "vyatta-msdp-configure --routing-instance $VAR(../../@)";
			}
			refine msdp/peer {
				configd:validate "vyatta-msdp-validate --routing-instance $VAR(../../../@) -- --level peer --param $VAR(@)";
			}
		}
	}
}
