module vyatta-protocols-interface-validation-mpls-v1 {
	namespace "urn:vyatta.com:mgmt:vyatta-protocols-interface-validation-mpls:1";
	prefix vyatta-protocols-interface-validation-mpls-v1;

	import vyatta-interfaces-v1 {
		prefix if;
	}
	import vyatta-interfaces-dataplane-v1 {
		prefix if-dataplane;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for vyatta-protocols-interface-validation-mpls-v1";

	revision 2016-06-14 {
		description "Initial revision of version 1";
	}

	grouping interface-mpls {
		configd:allowed "vyatta-interfaces.pl --show=dataplane";
		leaf interface {
			description "Interface which supports mpls";
			type string {
				configd:help "Interface name";
			}
			must  "(current() = /if:interfaces/if-dataplane:dataplane/if-dataplane:tagnode)"
				+"or (substring-after(current(), '.') = /if:interfaces/if-dataplane:dataplane"
				+"[if-dataplane:tagnode = substring-before(current(), '.')]/if-dataplane:vif/if-dataplane:tagnode)" {
				error-message "Interface name must refer to an existing mpls-capable interface name";
			}
		}
	}
}
