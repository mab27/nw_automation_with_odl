module vyatta-protocols-rib-routing-instance-v1 {
	namespace "urn:vyatta.com:mgmt:vyatta-protocols-rib-routing-instance:1";
	prefix vyatta-protocols-rib-routing-instance-v1;

	import vyatta-protocols-rib-v1 {
		prefix vyatta-rib;
	}
	import configd-v1 {
		prefix configd;
	}
	import vyatta-routing-v1 {
		prefix vyatta-routing;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for vyatta-protocols-rib-routing-instance-v1";

	revision 2016-05-02 {
		description "Initial revision of version 1";
	}

	augment /vyatta-routing:routing/vyatta-routing:routing-instance/vyatta-routing:protocols {
		container rib {
			configd:priority "650";
			configd:help "Routing Information Base (RIB) parameters";
			description "Routing Information Base (RIB) parameters";
			container log {
				configd:help "RIB logging parameters";
				description "RIB logging parameters";
				uses vyatta-rib:log-all; 
				uses vyatta-rib:log-events;
				uses vyatta-rib:log-packet;
			}
		}
	}
}
