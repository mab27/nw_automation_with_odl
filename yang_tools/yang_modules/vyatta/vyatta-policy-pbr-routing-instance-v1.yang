module vyatta-policy-pbr-routing-instance-v1 {
	namespace "urn:vyatta.com:mgmt:vyatta-policy-pbr-routing-instance:1";
	prefix vyatta-policy-pbr-routing-instance-v1;

        import vyatta-policy-pbr-v1 {
                prefix pbr;
        }
	import vyatta-policy-v1 {
		prefix policy;
	}
	import vyatta-policy-route-v1 {
		prefix policy-route;
	}
	import vyatta-routing-v1 {
		prefix routing;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 YANG module for PBR routing instances.";

	revision 2016-04-14 {
		description "Initial revision.";
	}

	augment /policy:policy/policy-route:route/pbr:pbr/pbr:rule {
		uses routing:routing-instance-or-default-leaf {
			refine routing-instance {
				must "(current() = 'default') or
					(/routing:routing/routing:routing-instance[routing:instance-name = current()]/routing:instance-type = 'vrf')" {
					error-message "Routing instance must be of type VRF, or be 'default'";
				}
			}
		}
	}
}
