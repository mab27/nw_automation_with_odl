module vyatta-protocols-mpls-v1 {
	namespace "urn:vyatta.com:mgmt:vyatta-protocols-mpls:1";
	prefix protocols-mpls;

	import vyatta-protocols-v1 {
		prefix protocols;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2015-2016 by Brocade Communications Systems, Inc.
		 All rights reserved.

		 The YANG module package for vyatta-protocols-mpls-v1";

	revision 2015-07-28 {
		description "Initial revision.";
	}

	typedef mpls-label-unreserved {
		type uint32 {
			range 16..1048575;
		}
		description "MPLS label range of unreserved values";
	}

	augment /protocols:protocols {
		container mpls {
			configd:priority "600";
			configd:help "MPLS infrastructure";
			configd:end "vyatta-mpls.pl --main";
			container label-range {
				configd:help "Create the label space";
				leaf maximum-label-value {
					configd:help "Specify maximum label value";
					type mpls-label-unreserved;
					default 1048575;
				}
				leaf minimum-label-value {
					configd:help "Specify minimum label value";
					type mpls-label-unreserved;
					default 16;
				}
				must "minimum-label-value < maximum-label-value";
			}
			leaf disable-ip-propagate-ttl {
				configd:help "Disable propagate IP TTL";
				type empty;
			}
			leaf default-ttl {
				configd:help "Default TTL when not propagating IP TTL";
				type uint8;
				default 255;
			}
		}
	}
}
