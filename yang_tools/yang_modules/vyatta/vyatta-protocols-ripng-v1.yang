module vyatta-protocols-ripng-v1 {
	namespace "urn:vyatta.com:mgmt:vyatta-protocols-ripng:1";
	prefix vyatta-protocols-ripng-v1;

	import vyatta-types-v1 {
		prefix types;
	}
	import vyatta-protocols-v1 {
		prefix protocols;
	}
	import configd-v1 {
		prefix configd;
	}
	import vyatta-interfaces-v1 {
		prefix if;
	}
	import vyatta-interfaces-bridge-v1 {
		prefix interfaces-bridge;
	}
	import vyatta-interfaces-dataplane-v1 {
		prefix interfaces-dataplane;
	}
	import vyatta-interfaces-l2tpeth-v1 {
		prefix interfaces-l2tpeth;
	}
	import vyatta-interfaces-loopback-v1 {
		prefix interfaces-loopback;
	}
	import vyatta-interfaces-openvpn-v1 {
		prefix interfaces-openvpn;
	}
	import vyatta-interfaces-tunnel-v1 {
		prefix interfaces-tunnel;
	}
	import vyatta-interfaces-vti-v1 {
		prefix interfaces-vti;
	}
	import vyatta-interfaces-bonding-v1 {
		prefix interfaces-bonding;
	}
	import vyatta-policy-v1 {
		prefix policy;
	}
	import vyatta-policy-route-v1 {
		prefix policy-route;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module package for vyatta-protocols-ripng-v1";

	revision 2016-07-19 {
		description
			"- Allow non link-local address as neighbor address on l2tpeth
				interfaces for backward	compatibility.
			 - Relax interface validation to allow non-existing interface.
			 - Group containers 'ripng' and 'packet'.
			 - Import vyatta-protocols-interface-validation-v1 module for
				interface validation.
			 - Import vyatta-policy-v1 and vyatta-policy-route-v1 modules
				to refer to their access-list and prefix-list nodes.
			 - Add description to all nodes.";
	}

	revision 2015-08-06 {
		description "Initial revision of version 1";
	}

	grouping ripng-log-packet {
		container packet {
			configd:help "RIPNG packet logs";
			description "RIPNG packet logs";
			leaf all {
				type empty;
				configd:help "Enable RIPNG packet all logs";
				description "Enable RIPNG packet all logs";
				configd:create "/opt/vyatta/share/tmplscripts/protocols/ripng/log/packet/configd_create.sh";
				configd:delete "/opt/vyatta/share/tmplscripts/protocols/ripng/log/packet/configd_delete.sh";
			}
			leaf send {
				type empty;
				configd:help "Enable RIPNG packet send logs";
				description "Enable RIPNG packet send logs";
				configd:create "/opt/vyatta/share/tmplscripts/protocols/ripng/log/packet/configd_create.sh";
				configd:delete "/opt/vyatta/share/tmplscripts/protocols/ripng/log/packet/configd_delete.sh";
			}
			leaf recv {
				type empty;
				configd:help "Enable RIPNG packet recv logs";
				description "Enable RIPNG packet recv logs";
				configd:create "/opt/vyatta/share/tmplscripts/protocols/ripng/log/packet/configd_create.sh";
				configd:delete "/opt/vyatta/share/tmplscripts/protocols/ripng/log/packet/configd_delete.sh";
			}
			leaf detail {
				type empty;
				configd:help "Enable RIPNG packet detail logs";
				description "Enable RIPNG packet detail logs";
				configd:create "/opt/vyatta/share/tmplscripts/protocols/ripng/log/packet/configd_create.sh";
				configd:delete "/opt/vyatta/share/tmplscripts/protocols/ripng/log/packet/configd_delete.sh";
			}
		}
	}

	grouping ripng-protocol {
		container ripng {
			presence "true";
			configd:priority "660";
			configd:help "Routing Information Protocol (RIPng) parameters";
			description "Routing Information Protocol (RIPng) parameters";
			configd:create "/opt/vyatta/share/tmplscripts/protocols/ripng/configd_create.sh";
			configd:delete "/opt/vyatta/share/tmplscripts/protocols/ripng/configd_delete.sh";
			leaf-list aggregate-address {
				type types:ipv6-prefix {
					configd:normalize "normalize ipv6-prefix";
				}
				ordered-by "user";
				configd:help "Aggregate RIPng route announcement";
				description "Aggregate RIPng route announcement";
				configd:create "/opt/vyatta/share/tmplscripts/protocols/ripng/aggregate-address/configd_create.sh";
				configd:delete "/opt/vyatta/share/tmplscripts/protocols/ripng/aggregate-address/configd_delete.sh";
			}
			leaf-list route {
				type types:ipv6-prefix {
					configd:normalize "normalize ipv6-prefix";
				}
				ordered-by "user";
				configd:help "RIPng static route";
				description "RIPng static route";
				configd:create "/opt/vyatta/share/tmplscripts/protocols/ripng/route/configd_create.sh";
				configd:delete "/opt/vyatta/share/tmplscripts/protocols/ripng/route/configd_delete.sh";
			}
			container timers {
				presence "true";
				configd:help "RIPng timer values";
				description "RIPng timer values";
				configd:end "/opt/vyatta/share/tmplscripts/protocols/ripng/timers/configd_end.sh";
				leaf garbage-collection {
					type uint32 {
						range 5..65535 {
							error-message "Garbage collection timer must be between 5 and 65535";
						}
					}
					default "120";
					configd:help "Garbage collection timer";
					description "Garbage collection timer";
				}
				leaf update {
					type uint32 {
						range 5..65535 {
							error-message "Update timer must be between 5 and 65535";
						}
					}
					default "30";
					configd:help "Routing table update timer";
					description "Routing table update timer";
				}
				leaf timeout {
					type uint32 {
						range 5..65535 {
							error-message "Timeout timer must be between 5 and 65535";
						}
					}
					default "180";
					configd:help "Routing information timeout timer";
					description "Routing information timeout timer";
				}
			}
			container distribute-list {
				presence "true";
				configd:help "Filter networks in routing updates";
				description "Filter networks in routing updates";
				container access-list {
					presence "true";
					configd:help "Access list";
					description "Access list";
					leaf out {
						type leafref {
							path "/policy:policy/policy-route:route/policy-route:access-list6/policy-route:tagnode";
						}
						configd:help "Access list to apply to output packets";
						description "Access list to apply to output packets";
						configd:update "/opt/vyatta/share/tmplscripts/protocols/ripng/distribute-list/access-list/out/configd_update.sh";
						configd:delete "/opt/vyatta/share/tmplscripts/protocols/ripng/distribute-list/access-list/out/configd_delete.sh";
					}
					leaf in {
						type leafref {
							path "/policy:policy/policy-route:route/policy-route:access-list6/policy-route:tagnode";
						}
						configd:help "Access list to apply to input packets";
						description "Access list to apply to input packets";
						configd:update "/opt/vyatta/share/tmplscripts/protocols/ripng/distribute-list/access-list/in/configd_update.sh";
						configd:delete "/opt/vyatta/share/tmplscripts/protocols/ripng/distribute-list/access-list/in/configd_delete.sh";
					}
				}
				list interface {
					configd:help "Apply filtering to an interface";
					description "Apply filtering to an interface";
					configd:allowed "/opt/vyatta/share/tmplscripts/protocols/ripng/distribute-list/interface/configd_allowed.sh";
					key "tagnode";
					leaf tagnode {
						type types:interface-ifname;
						configd:help "Apply filtering to an interface";
						description "Apply filtering to an interface";
					}
					container access-list {
						presence "true";
						configd:help "Access list";
						description "Access list";
						leaf out {
							type leafref {
								path "/policy:policy/policy-route:route/policy-route:access-list/policy-route:tagnode";
							}
							configd:help "Access list to apply to output packets";
							description "Access list to apply to output packets";
							configd:update "/opt/vyatta/share/tmplscripts/protocols/ripng/distribute-list/interface/access-list/out/configd_update.sh";
							configd:delete "/opt/vyatta/share/tmplscripts/protocols/ripng/distribute-list/interface/access-list/out/configd_delete.sh";
						}
						leaf in {
							type leafref {
								path "/policy:policy/policy-route:route/policy-route:access-list/policy-route:tagnode";
							}
							configd:help "Access list to apply to input packets";
							description "Access list to apply to input packets";
							configd:update "/opt/vyatta/share/tmplscripts/protocols/ripng/distribute-list/interface/access-list/in/configd_update.sh";
							configd:delete "/opt/vyatta/share/tmplscripts/protocols/ripng/distribute-list/interface/access-list/in/configd_delete.sh";
						}
					}
					container prefix-list {
						presence "true";
						configd:help "Prefix-list";
						description "Prefix-list";
						leaf out {
							type leafref {
								path "/policy:policy/policy-route:route/policy-route:prefix-list6/policy-route:tagnode";
							}
							configd:help "Prefix-list to apply to output packets";
							description "Prefix-list to apply to output packets";
							configd:update "/opt/vyatta/share/tmplscripts/protocols/ripng/distribute-list/interface/prefix-list/out/configd_update.sh";
							configd:delete "/opt/vyatta/share/tmplscripts/protocols/ripng/distribute-list/interface/prefix-list/out/configd_delete.sh";
						}
						leaf in {
							type leafref {
								path "/policy:policy/policy-route:route/policy-route:prefix-list6/policy-route:tagnode";
							}
							configd:help "Prefix-list to apply to input packets";
							description "Prefix-list to apply to input packets";
							configd:update "/opt/vyatta/share/tmplscripts/protocols/ripng/distribute-list/interface/prefix-list/in/configd_update.sh";
							configd:delete "/opt/vyatta/share/tmplscripts/protocols/ripng/distribute-list/interface/prefix-list/in/configd_delete.sh";
						}
					}
				}
				container prefix-list {
					presence "true";
					configd:help "Prefix-list";
					description "Prefix-list";
					leaf out {
						type leafref {
							path "/policy:policy/policy-route:route/policy-route:prefix-list6/policy-route:tagnode";
						}
						configd:help "Prefix-list to apply to output packets";
						description "Prefix-list to apply to output packets";
						configd:update "/opt/vyatta/share/tmplscripts/protocols/ripng/distribute-list/prefix-list/out/configd_update.sh";
						configd:delete "/opt/vyatta/share/tmplscripts/protocols/ripng/distribute-list/prefix-list/out/configd_delete.sh";
					}
					leaf in {
						type leafref {
							path "/policy:policy/policy-route:route/policy-route:prefix-list6/policy-route:tagnode";
						}
						configd:help "Prefix-list to apply to input packets";
						description "Prefix-list to apply to input packets";
						configd:update "/opt/vyatta/share/tmplscripts/protocols/ripng/distribute-list/prefix-list/in/configd_update.sh";
						configd:delete "/opt/vyatta/share/tmplscripts/protocols/ripng/distribute-list/prefix-list/in/configd_delete.sh";
					}
				}
			}
			leaf-list passive-interface {
				type types:interface-ifname;
				ordered-by "user";
				configd:help "Suppress routing updates on an interface";
				description "Suppress routing updates on an interface";
				configd:allowed "/opt/vyatta/share/tmplscripts/protocols/ripng/passive-interface/configd_allowed.sh";
				configd:create "/opt/vyatta/share/tmplscripts/protocols/ripng/passive-interface/configd_create.sh";
				configd:delete "/opt/vyatta/share/tmplscripts/protocols/ripng/passive-interface/configd_delete.sh";
			}
			leaf default-metric {
				type uint32 {
					range 1..16 {
						error-message "Must be between 1-16";
					}
				}
				configd:help "Metric of redistributed routes";
				description "Metric of redistributed routes";
				configd:update "/opt/vyatta/share/tmplscripts/protocols/ripng/default-metric/configd_update.sh";
				configd:delete "/opt/vyatta/share/tmplscripts/protocols/ripng/default-metric/configd_delete.sh";
			}
			container redistribute {
				presence "true";
				configd:help "Redistribute information from another routing protocol";
				description "Redistribute information from another routing protocol";
				container bgp {
					presence "true";
					configd:help "Redistribute BGP routes";
					description "Redistribute BGP routes";
					configd:end "/opt/vyatta/share/tmplscripts/protocols/ripng/redistribute/configd_redist_end.sh";
					leaf route-map {
						type leafref {
							path "/policy:policy/policy-route:route/policy-route:route-map/policy-route:tagnode";
						}
						configd:help "Route map reference";
						description "Route map reference";
					}
					leaf metric {
						type uint32 {
							range 1..16 {
								error-message "metric must be between 1 and 16";
							}
						}
						configd:help "Metric for redistributed routes";
						description "Metric for redistributed routes";
					}
				}
				container kernel {
					presence "true";
					configd:help "Redistribute kernel routes";
					description "Redistribute kernel routes";
					configd:end "/opt/vyatta/share/tmplscripts/protocols/ripng/redistribute/configd_redist_end.sh";
					leaf route-map {
						type leafref {
							path "/policy:policy/policy-route:route/policy-route:route-map/policy-route:tagnode";
						}
						configd:help "Route map reference";
						description "Route map reference";
					}
					leaf metric {
						type uint32 {
							range 1..16 {
								error-message "metric must be between 1 and 16";
							}
						}
						configd:help "Metric for redistributed routes";
						description "Metric for redistributed routes";
					}
				}
				container connected {
					presence "true";
					configd:help "Redistribute connected routes";
					description "Redistribute connected routes";
					configd:end "/opt/vyatta/share/tmplscripts/protocols/ripng/redistribute/configd_redist_end.sh";
					leaf route-map {
						type leafref {
							path "/policy:policy/policy-route:route/policy-route:route-map/policy-route:tagnode";
						}
						configd:help "Route map reference";
						description "Route map reference";
					}
					leaf metric {
						type uint32 {
							range 1..16 {
								error-message "metric must be between 1 and 16";
							}
						}
						configd:help "Metric for redistributed routes";
						description "Metric for redistributed routes";
					}
				}
				container static {
					presence "true";
					configd:help "Redistribute static routes";
					description "Redistribute static routes";
					configd:end "/opt/vyatta/share/tmplscripts/protocols/ripng/redistribute/configd_redist_end.sh";
					leaf route-map {
						type leafref {
							path "/policy:policy/policy-route:route/policy-route:route-map/policy-route:tagnode";
						}
						configd:help "Route map reference";
						description "Route map reference";
					}
					leaf metric {
						type uint32 {
							range 1..16 {
								error-message "metric must be between 1 and 16";
							}
						}
						configd:help "Metric for redistributed routes";
						description "Metric for redistributed routes";
					}
				}
				container ospfv3 {
					presence "true";
					configd:help "Redistribute OSPFv3 routes";
					description "Redistribute OSPFv3 routes";
					configd:end "/opt/vyatta/share/tmplscripts/protocols/ripng/redistribute/configd_redist_end.sh";
					leaf route-map {
						type leafref {
							path "/policy:policy/policy-route:route/policy-route:route-map/policy-route:tagnode";
						}
						configd:help "Route map reference";
						description "Route map reference";
					}
					leaf metric {
						type uint32 {
							range 1..16 {
								error-message "metric must be between 1 and 16";
							}
						}
						configd:help "Metric for redistributed routes";
						description "Metric for redistributed routes";
					}
				}
			}
			container default-information {
				presence "true";
				configd:help "Control distribution of default route";
				description "Control distribution of default route";
				leaf originate {
					type empty;
					configd:help "Distribute a default route";
					description "Distribute a default route";
					configd:create "/opt/vyatta/share/tmplscripts/protocols/ripng/default-information/originate/configd_create.sh";
					configd:delete "/opt/vyatta/share/tmplscripts/protocols/ripng/default-information/originate/configd_delete.sh";
				}
			}
		}
	}

	augment /protocols:protocols {
		uses ripng-protocol;
	}

	augment /protocols:protocols/ripng {
		container log {
			configd:help "RIPNG logging parameters";
			description "RIPNG logging parameters";
			leaf all {
				type empty;
				configd:help "Enable all RIPNG logs";
				description "Enable all RIPNG logs";
				configd:create "/opt/vyatta/share/tmplscripts/protocols/ripng/log/configd_create.sh";
				configd:delete "/opt/vyatta/share/tmplscripts/protocols/ripng/log/configd_delete.sh";
			}
			leaf events {
				type empty;
				configd:help "Enable RIPNG events logs";
				description "Enable RIPNG events logs";
				configd:create "/opt/vyatta/share/tmplscripts/protocols/ripng/log/configd_create.sh";
				configd:delete "/opt/vyatta/share/tmplscripts/protocols/ripng/log/configd_delete.sh";
			}
			leaf rib {
				type empty;
				configd:help "Enable RIPNG rib logs";
				description "Enable RIPNG rib logs";
				configd:create "/opt/vyatta/share/tmplscripts/protocols/ripng/log/configd_create.sh";
				configd:delete "/opt/vyatta/share/tmplscripts/protocols/ripng/log/configd_delete.sh";
			}
			leaf nsm {
				type empty;
				configd:help "Enable RIPNG nsm logs";
				description "Enable RIPNG nsm logs";
				configd:create "/opt/vyatta/share/tmplscripts/protocols/ripng/log/configd_create.sh";
				configd:delete "/opt/vyatta/share/tmplscripts/protocols/ripng/log/configd_delete.sh";
			}
			uses ripng-log-packet;
		}
	}

	grouping itf-ipv6-ripng {
		container ripng {
			configd:help "Routing Information Protocol (RIPng)";
			description "Routing Information Protocol (RIPng)";
			container split-horizon {
				presence "true";
				configd:help "Split horizon parameters";
				description "Split horizon parameters";
				leaf poison-reverse {
					type empty;
					configd:help "Enable poison reverse for split-horizon";
					description "Enable poison reverse for split-horizon";
					configd:create "/opt/vyatta/share/tmplscripts/interfaces/all/ipv6/ripng/split-horizon/poison-reverse/configd_create.sh";
					configd:delete "/opt/vyatta/share/tmplscripts/interfaces/all/ipv6/ripng/split-horizon/poison-reverse/configd_delete.sh";
					must "not(../disable)" {
						error-message "You cannot configure 'split-horizon poison-reverse' and 'split-horizon disable' on the same interface";
					}
				}
				leaf disable {
					type empty;
					configd:help "Disable split horizon";
					description "Disable split horizon";
					configd:create "/opt/vyatta/share/tmplscripts/interfaces/all/ipv6/ripng/split-horizon/disable/configd_create.sh";
					configd:delete "/opt/vyatta/share/tmplscripts/interfaces/all/ipv6/ripng/split-horizon/disable/configd_delete.sh";
					must "not(../poison-reverse)" {
						error-message "You cannot configure 'split-horizon poison-reverse' and 'split-horizon disable' on the same interface";
					}
				}
			}
			leaf metric-offset {
				type uint32 {
					range 1..16 {
						error-message "Must be between 1-16";
					}
				}
				configd:help "metric value";
				description "metric value";
				configd:update "/opt/vyatta/share/tmplscripts/interfaces/all/ipv6/ripng/metric-offset/configd_update.sh";
				configd:delete "/opt/vyatta/share/tmplscripts/interfaces/all/ipv6/ripng/metric-offset/configd_delete.sh";
			}
			leaf enable {
				type empty;
				configd:help "Enable RIPng for interface";
				description "Enable RIPng for interface";
				configd:create "/opt/vyatta/share/tmplscripts/interfaces/all/ipv6/ripng/enable/configd_create.sh";
				configd:delete "/opt/vyatta/share/tmplscripts/interfaces/all/ipv6/ripng/enable/configd_delete.sh";
			}
			leaf neighbor {
				type types:ipv6-address;
				configd:help "IPv6 Link local address of neighbor";
				description "IPv6 Link local address of neighbor";
				configd:update "/opt/vyatta/share/tmplscripts/interfaces/all/ipv6/ripng/neighbor/configd_update.sh";
				configd:delete "/opt/vyatta/share/tmplscripts/interfaces/all/ipv6/ripng/neighbor/configd_delete.sh";
				configd:validate "/opt/vyatta/share/tmplscripts/interfaces/all/ipv6/ripng/neighbor/configd_validate.sh";
				must "(../../../interfaces-l2tpeth:l2tp-session or ../../../../interfaces-l2tpeth:l2tp-session)"
				    + "or ((starts-with(current(), 'fe8'))"
						+ "or (starts-with(current(), 'fe9'))"
						+ "or (starts-with(current(), 'fea'))"
						+ "or (starts-with(current(), 'feb')))" {
					error-message "Neighbor address must be link local";
				}
			}
		}
	}
	augment /if:interfaces/interfaces-bridge:bridge/interfaces-bridge:ipv6 {
		uses itf-ipv6-ripng;
	}
	augment /if:interfaces/interfaces-dataplane:dataplane/interfaces-dataplane:ipv6 {
		uses itf-ipv6-ripng;
	}
	augment /if:interfaces/interfaces-dataplane:dataplane/interfaces-dataplane:vif/interfaces-dataplane:ipv6 {
		uses itf-ipv6-ripng;
	}
	augment /if:interfaces/interfaces-l2tpeth:l2tpeth/interfaces-l2tpeth:ipv6 {
		uses itf-ipv6-ripng;
	}
	augment /if:interfaces/interfaces-l2tpeth:l2tpeth/interfaces-l2tpeth:vif/interfaces-l2tpeth:ipv6 {
		uses itf-ipv6-ripng;
	}
	augment /if:interfaces/interfaces-loopback:loopback/interfaces-loopback:ipv6 {
		uses itf-ipv6-ripng;
	}
	augment /if:interfaces/interfaces-openvpn:openvpn/interfaces-openvpn:ipv6 {
		uses itf-ipv6-ripng;
	}
	augment /if:interfaces/interfaces-tunnel:tunnel/interfaces-tunnel:ipv6 {
		uses itf-ipv6-ripng;
	}
	augment /if:interfaces/interfaces-vti:vti/interfaces-vti:ipv6 {
		uses itf-ipv6-ripng;
	}
	augment /if:interfaces/interfaces-bonding:bonding/interfaces-bonding:ipv6 {
		uses itf-ipv6-ripng;
	}
	augment /if:interfaces/interfaces-bonding:bonding/interfaces-bonding:vif/interfaces-bonding:ipv6 {
		uses itf-ipv6-ripng;
	}
}
