module vyatta-interfaces-v1 {
	namespace "urn:vyatta.com:mgmt:vyatta-interfaces:1";
	prefix vyatta-if-v1;

	import configd-v1 { prefix configd; }
	import vyatta-types-v1 { prefix types; }

	organization "Brocade Communications Systems, Inc.";
	contact
		"Brocade Communications Systems, Inc.
		 Postal: 130 Holger Way
		 	 San Jose, CA 95134
		 E-mail: support@Brocade.com
		 Web: www.brocade.com";

	description
		"Copyright (c) 2014-2016 by Brocade Communications Systems, Inc.
		 All rights reserved.

		 This module implements vyatta-interfaces-v1.";

	revision 2016-08-24 {
		description "Refactor groupings to support system (host) interfaces";
	}
	revision 2016-03-28 {
		description "Remove use of bash in action scripts";
	}
	revision 2015-08-05 {
		description "Initial revision of version 1.";
	}

	typedef address {
		type union {
			type types:ipv4-prefix {
				configd:help "IPv4 Address";
				configd:syntax "valid_address $VAR(@)";
			}
			type types:ipv6-prefix {
				configd:help "IPv6 Address";
				configd:syntax "valid_address $VAR(@)";
			}
			configd:normalize "normalize ip";
		}
	}

	typedef address-dhcp {
		type union {
			type enumeration {
				enum dhcp {
					configd:help "Use DHCP to acquire an address";
				}
				enum dhcpv6  {
					configd:help "Use DHCPv6 to acquire an address";
				}
			}
			type address;
			configd:normalize "normalize ip";
		}
	}

	typedef description {
		type string {
			length "1..256";
		}
	}

	grouping if-status {
		leaf admin-status {
			type enumeration {
				enum up;
				enum down;
				enum testing;
			}
			description "Interface's desired state";
			config false;
		}
		leaf oper-status {
			type enumeration {
				enum up;
				enum down;
				enum testing;
				enum unknown;
				enum dormant;
				enum notpresent;
				enum lowerlayerdown;
			}
			description "Interface's current operational state";
			config false;
		}
	}

	grouping if-parameters-base {
		leaf disable {
			type empty;
			configd:help "Disable interface";
			configd:create "ip link set $VAR(../@) down";
		}
		leaf disable-link-detect {
			type empty;
			configd:help "Ignore link state changes";
			configd:create "vyatta-link-detect $VAR(../@) off";
			configd:delete "vyatta-link-detect $VAR(../@) on";
		}
		container ip {
			configd:help "IPv4 parameters";

			leaf enable-proxy-arp {
				type empty;
				configd:help "Enable proxy-arp on this interface";
				configd:create "sysctl -wq /net/ipv4/conf/$VAR(../../@)/proxy_arp=1";
				configd:delete "sysctl -wq /net/ipv4/conf/$VAR(../../@)/proxy_arp=0";
			}
			leaf rpf-check {
				type enumeration {
					enum "disable" {
						value 0;
						configd:help "No source validation";
					}
					enum "strict" {
						value 1;
						configd:help "Enable Strict Reverse Path Forwarding as defined in RFC3704";
					}
					enum "loose" {
						value 2;
						configd:help "Enable Loose Reverse Path Forwarding as defined in RFC3704";
					}
				}
				configd:help "Reverse path filter policy (see RFC3704)";
				default "disable";
				configd:update "set-rpf-check $VAR(@) $VAR(../../@)";
				configd:delete "set-rpf-check disable $VAR(../../@)";
			}
			leaf gratuitous-arp-count {
				type uint32 {
					range 0..10;
				}
				configd:help "# of unsolicited arps sent on link up (0 to disable)";
				default "1";
			}
		}

		container ipv6 {
			configd:help "IPv6 parameters";
		}
	}

	grouping if-parameter-description {
		leaf description {
			type description;
			description "Interface description";
			configd:help "Interface Description";
			configd:update "ip li set dev $VAR(../@) alias '$VAR(@)'";
			configd:delete "vyatta-interfaces.pl --dev=$VAR(../@) --delete-description";
		}
	}

	grouping if-parameter-log-martians {
		leaf log_martians {
			type empty;
			description "Enable the logging of bogus packets";
			configd:help "Enable the logging of bogus packets";
			configd:create "sysctl -wq /net/ipv4/conf/$VAR(../@)/log_martians=1";
			configd:delete "sysctl -wq /net/ipv4/conf/$VAR(../@)/log_martians=0";
		}
	}

	grouping if-parameters-host {
		description "Attributes used by host (administrative) interfaces";
		uses if-parameter-description;
		uses if-parameters-base;
		uses if-parameter-log-martians;
	}

	grouping if-parameters {
		description "Attributes used by forwarding interfaces";
		uses if-parameter-description;
		uses if-parameters-base {
			augment ip {
				leaf disable-forwarding {
					type empty;
					configd:help "Disable IPv4 forwarding on this interface";
					configd:create "sysctl -wq /net/ipv4/conf/$VAR(../../@)/forwarding=0";
					configd:delete "sysctl -wq /net/ipv4/conf/$VAR(../../@)/forwarding=1";
				}
			}
		}
		uses if-parameter-log-martians;
	}

	grouping vif-parameters-ip-base {
		description "Attributes used to manage IPv4 operations on sub-interfaces";

		leaf enable-proxy-arp {
			type empty;
			description "Enable proxy-arp on this interface";
			configd:help "Enable proxy-arp on this interface";
			configd:create "sysctl -wq /net/ipv4/conf/$VAR(../../../@).$VAR(../../@)/proxy_arp=1";
			configd:delete "sysctl -wq /net/ipv4/conf/$VAR(../../../@).$VAR(../../@)/proxy_arp=0";
		}
		leaf rpf-check {
			type enumeration {
				enum "disable" {
					value 0;
					description "No source validation";
					configd:help "No source validation";
				}
				enum "strict" {
					value 1;
					description "Enable Strict Reverse Path Forwarding as defined in RFC3704";
					configd:help "Enable Strict Reverse Path Forwarding as defined in RFC3704";
				}
				enum "loose" {
					value 2;
					description "Enable Loose Reverse Path Forwarding as defined in RFC3704";
					configd:help "Enable Loose Reverse Path Forwarding as defined in RFC3704";
				}
			}
			description "Reverse path filter policy (see RFC3704)";
			configd:help "Reverse path filter policy (see RFC3704)";
			default "disable";
			configd:update "set-rpf-check $VAR(@) $VAR(../../../@).$VAR(../../@)";
			configd:delete "set-rpf-check disable $VAR(../../../@).$VAR(../../@)";
		}
	}

	grouping vif-parameters-common {
		description "Attributes shared between host sub-interfaces and forwarding sub-interfaces";

		leaf disable {
			type empty;
			description "Disable this interface";
			configd:help "Disable interface";
			configd:create "ip link set $VAR(../../@).$VAR(../@) down";
		}
		leaf log_martians {
			type empty;
			description "Enable the logging of bogus packets";
			configd:help "Enable the logging of bogus packets";
			configd:create "sysctl -wq /net/ipv4/conf/$VAR(../../@).$VAR(../@)/log_martians=1";
			configd:delete "sysctl -wq /net/ipv4/conf/$VAR(../../@).$VAR(../@)/log_martians=0";
		}
		container ip {
			description "IPv4 interface parameters";
			configd:help "IPv4 parameters";
		}

		container ipv6 {
			description "IPv6 interface parameters";
			configd:help "IPv6 parameters";
		}
	}

	grouping vif-parameters-host {
		description "Attributes used by host (administrative) sub-interfaces";
		uses vif-parameters-common {
			augment ip {
				uses vif-parameters-ip-base;
			}
		}
	}

	grouping vif-parameters-base {
		description "Base attributes used by all forwarding sub-interfaces";
		uses vif-parameters-common {
			augment ip {
				leaf disable-forwarding {
					type empty;
					description "Disable IPv4 forwarding on this interface";
					configd:help "Disable IPv4 forwarding on this interface";
					configd:create "sysctl -wq /net/ipv4/conf/$VAR(../../../@).$VAR(../../@)/forwarding=0";
					configd:delete "sysctl -wq /net/ipv4/conf/$VAR(../../../@).$VAR(../../@)/forwarding=1";
				}
				uses vif-parameters-ip-base;
			}
		}
	}

	grouping vif-description {
		leaf description {
			type description;
			description "Virtual sub-interface description";
			configd:help "Virtual sub-interface Description";
			configd:update "ip li set dev $VAR(../../@).$VAR(../@) alias '$VAR(@)'";
			configd:delete "vyatta-interfaces.pl --dev=$VAR(../../@).$VAR(../@) --delete-description";
		}
	}

	grouping vif-parameters {
		uses vif-description;
		uses vif-parameters-base;
	}

	container interfaces {
		configd:help "Network interfaces";
		configd:begin "/opt/vyatta/sbin/vyatta-delete-addrs.pl";
		configd:end "/bin/run-parts ${vyatta_datarootdir}/tmplscripts${CONFIGD_PATH}/configd_end.d";
		configd:validate "vyatta-interfaces.pl --valid-addrs-commit";
	}
}
