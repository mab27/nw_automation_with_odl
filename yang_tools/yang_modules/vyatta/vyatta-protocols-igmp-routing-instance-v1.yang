module vyatta-protocols-igmp-routing-instance-v1 {
	namespace "urn:vyatta.com:mgmt:vyatta-protocols-igmp-routing-instance:1";
		prefix vyatta-protocols-igmp-routing-instance-v1;

	import configd-v1 {
		prefix configd;
	}
	import vyatta-routing-v1 {
		prefix routing;
	}
	import vyatta-protocols-igmp-v1 {
		prefix igmp;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-protocols-igmp-routing-instance-v1";

	revision 2016-04-22 {
		description "Add Routing Instance support for multicast 
			Augment /routing/routing-instance/protocols";
	}
	augment /routing:routing/routing:routing-instance/routing:protocols {
		uses igmp:igmp-parameters {
			refine igmp {
				configd:end "vyatta-igmp 4 --routing-instance $VAR(../../@)";
			}
		}
	}
}
