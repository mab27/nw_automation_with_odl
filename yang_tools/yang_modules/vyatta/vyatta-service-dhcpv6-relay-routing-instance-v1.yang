module vyatta-service-dhcpv6-relay-routing-instance-v1 {
	namespace "urn:vyatta.com:mgmt:vyatta-service-dhcpv6-relay-routing-instance:1";
	prefix vyatta-service-dhcpv6-relay-routing-instance-v1;

	import vyatta-service-dhcpv6-relay-v1 {
		prefix v6relay;
	}
	import vyatta-routing-v1 {
		prefix routing;
	}
	import configd-v1 {
		prefix configd;
	}
	import vyatta-interfaces-v1 {
		prefix if;
	}
	import vyatta-interfaces-bridge-v1 {
		prefix if-bridge;
	}
	import vyatta-interfaces-dataplane-v1 {
		prefix if-dataplane;
	}
	import vyatta-interfaces-bonding-v1 {
		prefix if-bonding;
	}
	import vyatta-routing-instance-interfaces-v1 {
		prefix rtintf;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-service-dhcpv6-relay-routing-instance-v1";

	revision 2016-07-12 {
		description "Initial revision of version 1.";
	}

	augment /routing:routing/routing:routing-instance/routing:service {
		uses v6relay:dhcpv6-relay-service {
			refine dhcpv6-relay/upstream-interface {
				configd:allowed "vyatta-show-interfaces.pl --vrf=$VAR(../../../@) --action=dhcp_allowed";
			}
			refine dhcpv6-relay/upstream-interface/tagnode {
				must "(current() = /if:interfaces/if-dataplane:dataplane/if-dataplane:tagnode)"
					+ "or (substring-after(current(), '.') = /if:interfaces/if-dataplane:dataplane"
					+ "[if-dataplane:tagnode = substring-before(current(), '.')]/if-dataplane:vif/if-dataplane:tagnode)"
					+ "or (current() = /if:interfaces/if-bridge:bridge/if-bridge:tagnode)"
					+ "or (current() = /if:interfaces/if-bonding:bonding/if-bonding:tagnode)"
					+ "or (substring-after(current(), '.') = /if:interfaces/if-bonding:bonding"
					+ "[if-bonding:tagnode = substring-before(current(), '.')]/if-bonding:vif/if-bonding:tagnode)" {
					error-message "upstream-interface name must refer to an existing dataplane, bonding or bridge interface name";
				}
				must "current() = /routing:routing/routing:routing-instance" +
					"[routing:instance-name = current()/../../../../routing:instance-name]" +
					"/rtintf:interface/rtintf:name" {
					error-message "Interface must be configured in this routing instance";
				}
			}
			refine dhcpv6-relay {
				configd:end "/opt/vyatta/share/tmplscripts/service/dhcpv6-relay/configd_vrf_end.sh";
			}
			refine dhcpv6-relay/listen-interface {
				configd:allowed "vyatta-show-interfaces.pl --vrf=$VAR(../../../@) --action=dhcp_allowed";
			}
			refine dhcpv6-relay/listen-interface/tagnode {
				must "(current() = /if:interfaces/if-dataplane:dataplane/if-dataplane:tagnode)"
					+ "or (substring-after(current(), '.') = /if:interfaces/if-dataplane:dataplane"
					+ "[if-dataplane:tagnode = substring-before(current(), '.')]/if-dataplane:vif/if-dataplane:tagnode)"
					+ "or (current() = /if:interfaces/if-bridge:bridge/if-bridge:tagnode)"
					+ "or (current() = /if:interfaces/if-bonding:bonding/if-bonding:tagnode)"
					+ "or (substring-after(current(), '.') = /if:interfaces/if-bonding:bonding"
					+ "[if-bonding:tagnode = substring-before(current(), '.')]/if-bonding:vif/if-bonding:tagnode)" {
					error-message "upstream-interface name must refer to an existing dataplane, bonding or bridge interface name";
				}
				must "current() = /routing:routing/routing:routing-instance" +
					"[routing:instance-name = current()/../../../../routing:instance-name]" +
					"/rtintf:interface/rtintf:name" {
					error-message "Interface must be configured in this routing instance";
				}
			}
		}
	}
}
