module vyatta-protocols-static-routing-instance-v1 {
	namespace "urn:vyatta.com:mgmt:vyatta-protocols-static-routing-instance:1";
	prefix vyatta-protocols-static-routing-instance-v1;

	import vyatta-routing-v1 {
		prefix vyatta-routing;
	}
	import vyatta-protocols-static-v1 {
		prefix vyatta-static;
	}
	import vyatta-routing-instance-interfaces-v1 {
		prefix routing-instance-if;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for
		 vyatta-protocols-static-route-routing-instance-v1";

	revision 2016-05-01 {
		description "Initial revision of version 1";
	}

	augment /vyatta-routing:routing/vyatta-routing:routing-instance/vyatta-routing:protocols {
		uses vyatta-static:static-route {
			refine static/route/next-hop/interface {
				must "(1 = count(/vyatta-routing:routing/vyatta-routing:routing-instance[vyatta-routing:instance-name =
					current()/../../../../../vyatta-routing:instance-name]/routing-instance-if:interface[routing-instance-if:name = current()]))" {
					error-message "next-hop interface doesn't belong to routing-instance";
				}
			}
			refine static/route6/next-hop/interface {
				must "(1 = count(/vyatta-routing:routing/vyatta-routing:routing-instance[vyatta-routing:instance-name =
					current()/../../../../../vyatta-routing:instance-name]/routing-instance-if:interface[routing-instance-if:name = current()]))" {
					error-message "next-hop interface doesn't belong to routing-instance";
				}
			}
		}
	}
}
