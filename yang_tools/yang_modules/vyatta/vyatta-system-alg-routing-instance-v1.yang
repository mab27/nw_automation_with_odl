module vyatta-system-alg-routing-instance-v1 {
	namespace "urn:vyatta.com:mgmt:vyatta-system-alg-routing-instance:1";
	prefix vyatta-system-alg-routing-instance-v1;

	import vyatta-routing-v1 {
		prefix rt-instance;
	}
	import vyatta-system-alg-v1 {
		prefix vyatta-alg;
	}

	organization "Brocade Communications Systems, Inc.";
	contact
		"Brocade Communications Systems, Inc.
		 Postal: 130 Holger Way
			 San Jose, CA 95134
		 E-mail: support@Brocade.com
		 Web: www.brocade.com";

	description
		"Copyright (c) 2016 by Brocade Communications Systems, Inc.
		 All rights reserved.

		 YANG module for Vyatta ALG configuration and operation for
		 routing instances.";

	revision 2016-04-14 {
		description "Initial revision.";
	}

	augment /rt-instance:routing/rt-instance:routing-instance/rt-instance:system {
		uses vyatta-alg:alg-grouping;
	}
}
