module vyatta-system-tacplus-routing-instance-v1 {
	namespace "urn:vyatta.com:mgmt:vyatta-system-tacplus-routing-instance:1";
	prefix vyatta-system-tacplus-routing-instance-v1;

	import vyatta-system-v1 {
		prefix system;
	}
	import vyatta-system-login-v1 {
		prefix system-login;
	}
	import vyatta-routing-v1 {
		prefix rt-instance;
	}
	import vyatta-system-tacplus-v1 {
		prefix system-tacplus;
	}

	organization "Brocade Communications Systems, Inc.";
	contact
		"Brocade Communications Systems, Inc.
		Postal: 130 Holger Way
		San Jose, CA 95134
		E-mail: support@Brocade.com
		Web: www.brocade.com";

	description
		"Copyright (c) 2016-2017 by Brocade Communications Systems, Inc.
		 All rights reserved.

		 The YANG module for vyatta-system-tacplus-routing-instance-v1";

    revision 2017-02-09 {
        description "Rework YANG nodeset != comparison";
    }
	revision 2016-02-19 {
		description "Add routing instance support for TACACS+";
	}

	augment /rt-instance:routing/rt-instance:routing-instance/rt-instance:system/rt-instance:login {
		uses system-tacplus:tacplus-system-login-grouping {
			refine tacplus-server {
				must "count(/system:system/system-login:login/system-tacplus:tacplus-server) = 0" {
					error-message "Cannot also configure TACACS+ in default routing-instance";
				}
				must "count(/rt-instance:routing/rt-instance:routing-instance[not(rt-instance:instance-name ="
				+ "current()/../../../rt-instance:instance-name)]/rt-instance:system/rt-instance:login/tacplus-server) = 0" {
					error-message "Cannot configure TACACS+ in more than one routing-instance simultaneously";
				}
			}
		} 
	}
}
