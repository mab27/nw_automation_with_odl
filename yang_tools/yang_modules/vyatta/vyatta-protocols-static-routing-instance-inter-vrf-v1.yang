module vyatta-protocols-static-routing-instance-inter-vrf-v1 {
	namespace "urn:vyatta.com:mgmt:vyatta-protocols-static-routing-instance-inter-vrf:1";
	prefix vyatta-protocols-static-routing-instance-inter-vrf-v1;

	import vyatta-protocols-static-routing-instance-v1 {
		prefix vyatta-static-routing-instance;
	}
	import vyatta-routing-v1 {
		prefix vyatta-routing;
	}
	import vyatta-protocols-static-v1 {
		prefix vyatta-static;
	}
	import vyatta-protocols-v1 {
		prefix protocols;
	}
	import configd-v1 {
		prefix configd;
	}
	import vyatta-routing-instance-interfaces-v1 {
		prefix routing-instance-interfaces;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for
		 vyatta-protocols-static-route-routing-instance-inter-vrf-v1";

	revision 2016-07-18 {
		description "Initial revision of version 1";
	}

	augment /protocols:protocols/vyatta-static:static/vyatta-static:route {
		list next-hop-routing-instance {
			configd:help "Destination Routing Instance for the next-hop";
			configd:allowed "/opt/vyatta/share/tmplscripts/protocols/static/route/next-hop-routing-instance/configd_allowed.sh";
			description "Destination Routing Instance for the next-hop";
			key "routing-instance";
			uses vyatta-routing:routing-instance-or-default-leaf;
			uses vyatta-static:static-route-ipv4-next-hop {
				refine next-hop/interface {
					must "(1 = count(/vyatta-routing:routing/vyatta-routing:routing-instance[vyatta-routing:instance-name =
						current()/../../routing-instance]/routing-instance-interfaces:interface[routing-instance-interfaces:name = current()]))"{
						error-message "next-hop interface doesn't belong to routing-instance";
					}
				}
				refine next-hop {
					must "disable or " +
						"(distance != ../../vyatta-static:blackhole/vyatta-static:distance and " +
						"distance != ../../vyatta-static:unreachable/vyatta-static:distance and " +
						"count(../../../vyatta-static:interface-route[vyatta-static:tagnode = current()/../../vyatta-static:tagnode]/vyatta-static:next-hop-interface[vyatta-static:distance = current()/distance])
						= count(../../../vyatta-static:interface-route[vyatta-static:tagnode = current()/../../vyatta-static:tagnode]/vyatta-static:next-hop-interface[vyatta-static:distance = current()/distance]/disable))" {
						error-message "Must not configure same distance for next-hop, interface-route and blackhole/unreachable"; 
					}
				}
			}
			must "routing-instance != 'default'" {
				error-message "inter-vrf route next-hop should be in a different routing-instance.";
			}
			must "next-hop" {
				error-message "Must configure a next-hop.";
			}
		}
	}

	augment /protocols:protocols/vyatta-static:static/vyatta-static:route6 {
		list next-hop-routing-instance {
			configd:help "Destination Routing Instance for the next-hop";
			configd:allowed "/opt/vyatta/share/tmplscripts/protocols/static/route/next-hop-routing-instance/configd_allowed.sh";
			description "Destination Routing Instance for the next-hop";
			key "routing-instance";
			uses vyatta-routing:routing-instance-or-default-leaf;
			uses vyatta-static:static-route-ipv6-next-hop {
				refine next-hop/interface {
					must "(1 = count(/vyatta-routing:routing/vyatta-routing:routing-instance[vyatta-routing:instance-name =
						current()/../../routing-instance]/routing-instance-interfaces:interface[routing-instance-interfaces:name = current()]))"{
						error-message "next-hop interface doesn't belong to routing-instance";
					}
				}
				refine next-hop {
					must "disable or " +
						"(distance != ../../vyatta-static:blackhole/vyatta-static:distance and " +
						"distance != ../../vyatta-static:unreachable/vyatta-static:distance and " +
						"count(../../../vyatta-static:interface-route6[vyatta-static:tagnode = current()/../../vyatta-static:tagnode]/vyatta-static:next-hop-interface[vyatta-static:distance = current()/distance])
						= count(../../../vyatta-static:interface-route6[vyatta-static:tagnode = current()/../../vyatta-static:tagnode]/vyatta-static:next-hop-interface[vyatta-static:distance = current()/distance]/disable))" {
						error-message "Must not configure same distance for next-hop, interface-route and blackhole/unreachable"; 
					}
				}

			}
			must "routing-instance != 'default'" { 
				error-message "inter-vrf route next-hop should be in a different routing-instance.";
			}
			must "next-hop" {
				error-message "Must configure a next-hop.";
			}
		}
	}


	augment /vyatta-routing:routing/vyatta-routing:routing-instance/vyatta-routing:protocols/vyatta-static-routing-instance:static/vyatta-static-routing-instance:route {
		list next-hop-routing-instance {
			configd:help "Destination Routing Instance for the next-hop";
			configd:allowed "/opt/vyatta/share/tmplscripts/protocols/static/route/next-hop-routing-instance/configd_allowed.sh";
			description "Destination Routing Instance for the next-hop";
			key "routing-instance";
			uses vyatta-routing:routing-instance-or-default-leaf;
			uses vyatta-static:static-route-ipv4-next-hop {
				refine next-hop/interface {
					must "((current()/../../routing-instance = 'default') and " +
						"(0 = count(/vyatta-routing:routing/vyatta-routing:routing-instance/
						routing-instance-interfaces:interface[routing-instance-interfaces:name = current()]))) or " + 
						"((current()/../../routing-instance != 'default') and " +
						"(1= count(/vyatta-routing:routing/vyatta-routing:routing-instance[vyatta-routing:instance-name = current()/../../routing-instance]/
						routing-instance-interfaces:interface[routing-instance-interfaces:name = current()])))" {
						error-message "next-hop interface doesn't belong to routing-instance";
					}
                                }
				refine next-hop {
					must "disable or " +
						"(distance != ../../vyatta-static-routing-instance:blackhole/vyatta-static-routing-instance:distance and " +
						"distance != ../../vyatta-static-routing-instance:unreachable/vyatta-static-routing-instance:distance and " +
						"count(../../../vyatta-static-routing-instance:interface-route[vyatta-static-routing-instance:tagnode = current()/../../vyatta-static-routing-instance:tagnode]/vyatta-static-routing-instance:next-hop-interface[vyatta-static-routing-instance:distance = current()/distance])
						= count(../../../vyatta-static-routing-instance:interface-route[vyatta-static-routing-instance:tagnode = current()/../../vyatta-static-routing-instance:tagnode]/vyatta-static-routing-instance:next-hop-interface[vyatta-static-routing-instance:distance = current()/distance]/disable))" {
						error-message "Must not configure same distance for next-hop, interface-route and blackhole/unreachable"; 
					}
				}
			}
			must "routing-instance != current()/../../../../vyatta-routing:instance-name" {
				error-message "inter-vrf route next-hop should be in a different routing-instance.";
			}
			must "next-hop" {
				error-message "next-hop must be configured.";
			}
		}
	}

	augment /vyatta-routing:routing/vyatta-routing:routing-instance/vyatta-routing:protocols/vyatta-static-routing-instance:static/vyatta-static-routing-instance:route6 {
		list next-hop-routing-instance-v6 {
			configd:help "Destination Routing Instance for the next-hop";
			configd:allowed "/opt/vyatta/share/tmplscripts/protocols/static/route/next-hop-routing-instance/configd_allowed.sh";
			description "Destination Routing Instance for the next-hop";
			key "routing-instance";
			uses vyatta-routing:routing-instance-or-default-leaf;
			uses vyatta-static:static-route-ipv6-next-hop {
				refine next-hop/interface {
					must "((current()/../../routing-instance = 'default') and " +
						"(0 = count(/vyatta-routing:routing/vyatta-routing:routing-instance/
						routing-instance-interfaces:interface[routing-instance-interfaces:name = current()]))) or " +
						"((current()/../../routing-instance != 'default') and " +
						"(1= count(/vyatta-routing:routing/vyatta-routing:routing-instance[vyatta-routing:instance-name = current()/../../routing-instance]/
						routing-instance-interfaces:interface[routing-instance-interfaces:name = current()])))" {
						error-message "next-hop interface doesn't belong to routing-instance";
					}		
				}
				refine next-hop {
					must "disable or " +
						"(distance != ../../vyatta-static-routing-instance:blackhole/vyatta-static-routing-instance:distance and " +
						"distance != ../../vyatta-static-routing-instance:unreachable/vyatta-static-routing-instance:distance and " +
						"count(../../../vyatta-static-routing-instance:interface-route6[vyatta-static-routing-instance:tagnode = current()/../../vyatta-static-routing-instance:tagnode]/vyatta-static-routing-instance:next-hop-interface[vyatta-static-routing-instance:distance = current()/distance])
						= count(../../../vyatta-static-routing-instance:interface-route6[vyatta-static-routing-instance:tagnode = current()/../../vyatta-static-routing-instance:tagnode]/vyatta-static-routing-instance:next-hop-interface[vyatta-static-routing-instance:distance = current()/distance]/disable))" {
						error-message "Must not configure same distance for next-hop, interface-route and blackhole/unreachable"; 
					}
				}
			}
			must "routing-instance != current()/../../../../vyatta-routing:instance-name" {
				error-message "inter-vrf route next-hop should be in a different routing-instance.";
			}
			must "next-hop" {
				error-message "next-hop must be configured.";
			}
		}
	}
}
