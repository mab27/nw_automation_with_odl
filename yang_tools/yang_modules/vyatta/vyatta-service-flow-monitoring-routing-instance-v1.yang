module vyatta-service-flow-monitoring-routing-instance-v1 {
	namespace "urn:vyatta.com:mgmt:vyatta-service-flow-monitoring-routing-instance:1";
	prefix vyatta-service-flow-monitoring-routing-instance-v1;

	import vyatta-services-v1 {
		prefix service;
	}
	import configd-v1 {
		prefix configd;
	}
	import vyatta-service-flow-monitoring-v1 {
		prefix flow-mon;
	}
	import vyatta-routing-v1 {
		prefix rd;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for
		 vyatta-service-flow-monitoring-routing-instance-v1";

	revision 2016-01-22 {
		description "Add Routing Domain support to flow-monitoring";
		configd:migration 1;
	}

	augment /service:service/flow-mon:flow-monitoring/flow-mon:exporter/flow-mon:udp-collector {
		leaf routing-instance {
			type leafref {
				path "/rd:routing/rd:routing-instance/rd:instance-name";
			}
			configd:help "Routing Domain used to export flows to collector";
			description "Routing Domain used to export flows to collector";
		}
	}
}
