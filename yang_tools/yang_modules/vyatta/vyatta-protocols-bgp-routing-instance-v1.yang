module vyatta-protocols-bgp-routing-instance-v1 {
	namespace "urn:vyatta.com:mgmt:vyatta-protocols-bgp-routing-instance:1";
	prefix vyatta-protocols-bgp-routing-instance-v1;

	import vyatta-protocols-v1 {
		prefix protocols;
	}
	import vyatta-protocols-bgp-v1 {
		prefix protocols-bgp;
	}
	import configd-v1 {
		prefix configd;
	}
	import vyatta-routing-v1 {
		prefix routing-instance;
	}

	organization "Brocade Communications Systems, Inc.";
	contact
		"Brocade Communications Systems, Inc.
		 Postal: 130 Holger Way
		 San Jose, CA 95134
		 E-mail: support@Brocade.com
		 Web: www.brocade.com";

	description
		"Copyright (c) 2016 by Brocade Communications Systems, Inc.
		 All rights reserved.

		 The YANG module for vyatta-protocols-bgp-routing-instance-v1";

	revision 2016-06-01 {
		description "Adding more debug logs and grouping them as well";
	}
	revision 2016-05-06 {
		description "Adding route-target and import-route-map configuration for vrf";
	}
	revision 2016-04-26 {
		description "Initial revision of version 1";
	}

	typedef rt-rd {
		type union {
			type string {
				//ASN:NN format. Allowing 2-byte:4-byte (65535:4294967295)
				pattern '([0-9]|[1-9]\d{1,3}|[1-5]\d{4}|6[0-4]\d{3}|65[0-4]\d{2}|655[0-2]\d|6553[0-5])'
					+ ':'
					+ '([0-9]|[1-9]\d{1,8}|[1-3]\d{9}|4[0-1]\d{8}|42[0-8]\d{7}|429[0-3]\d{6}|4294[0-8]\d{5}|'
					+ '42949[0-5]\d{4}|429496[0-6]\d{3}|4294967[0-1]\d{2}|42949672[0-8]\d|429496729[0-5])';
			}
			type string {
				//ASN:NN format. Allowing 4-byte:2-byte (4294967295:65535)
				pattern '([0-9]|[1-9]\d{1,8}|[1-3]\d{9}|4[0-1]\d{8}|42[0-8]\d{7}|429[0-3]\d{6}|4294[0-8]\d{5}|'
					+ '42949[0-5]\d{4}|429496[0-6]\d{3}|4294967[0-1]\d{2}|42949672[0-8]\d|429496729[0-5])'
					+ ':'
					+ '([0-9]|[1-9]\d{1,3}|[1-5]\d{4}|6[0-4]\d{3}|65[0-4]\d{2}|655[0-2]\d|6553[0-5])';
			}
			type string {
				//IPAddress:NN format. Allowing IpAddress:2-byte
				pattern '(([0-9]|[1-9][0-9]|1[0-9][0-9]|2[0-4][0-9]|25[0-5])\.){3}'
					+  '([0-9]|[1-9][0-9]|1[0-9][0-9]|2[0-4][0-9]|25[0-5])'
					+ ':'
					+ '([0-9]|[1-9]\d{1,3}|[1-5]\d{4}|6[0-4]\d{3}|65[0-4]\d{2}|655[0-2]\d|6553[0-5])';
			}
		}
	}

	/* Confederation identifier can be configured only in default routing-instance */
	grouping bgp-params-global-confederation-vrf {
		container confederation {
			description "AS confederation parameters for Non-default BGP Routing Instance";
			presence "BGP Confederation config";
			configd:help "AS confederation parameters";
			uses protocols-bgp:bgp-params-global-confederation-peers;
		} /*confederation*/
	}

	/* BGP Global parameters supported under routing-instance, limited set */
	grouping bgp-params-global-vrf {
		container parameters {
			description "BGP Global parameters that can be configured under Non-default BGP Routing Instance";
			presence "Enables BGP parameters";
			configd:help "BGP parameters";
			uses protocols-bgp:bgp-params-global-no-rtm;
			uses protocols-bgp:bgp-params-global-always-compare-med;
			uses protocols-bgp:bgp-params-global-default;
			uses bgp-params-global-confederation-vrf;
			uses protocols-bgp:bgp-params-global-bestpath;
			uses protocols-bgp:bgp-params-global-log-neighbor-changes;
			uses protocols-bgp:bgp-params-global-no-fast-external-failover;
			uses protocols-bgp:bgp-params-global-enforce-first-as;
			uses protocols-bgp:bgp-params-global-med-out-delay;
			uses protocols-bgp:bgp-params-global-no-client-to-client-reflection;
			uses protocols-bgp:bgp-params-global-deterministic-med;
			uses protocols-bgp:bgp-params-global-maximum-paths;
			uses protocols-bgp:bgp-params-global-router-id;
		}
	}

	/* BGP logging supported under routing-instance */
	grouping bgp-params-vrf-log {
		container log {
			description "BGP logging configuration parameters under Non-default BGP Routing Instance";
			configd:help "BGP logging parameters";
			uses protocols-bgp:bgp-params-log-all;
			uses protocols-bgp:bgp-params-log-events;
			uses protocols-bgp:bgp-params-log-filters;
			uses protocols-bgp:bgp-params-log-fsm;
			uses protocols-bgp:bgp-params-log-keepalive;
			uses protocols-bgp:bgp-params-log-update;
			uses protocols-bgp:bgp-params-log-bfd;
			uses protocols-bgp:bgp-params-log-dampening;
			uses protocols-bgp:bgp-params-log-msdp;
		}
	}

	grouping bgp-routing-instance {
		list bgp {
			configd:priority "730";
			description "BGP configuration parameters under Non-default Routing Instance";
			configd:help "Border Gateway Protocol (BGP) parameters";
			configd:end "/opt/vyatta/share/tmplscripts/protocols/bgp/configd_end_routing_instance.sh";

			must "count(../bgp/tagnode) <= 1" {
				error-message "Another BGP instance is already running" ;
			}
			/* Default BGP configuration is mandatory */
			must "(/protocols:protocols/protocols-bgp:bgp)" {
				error-message "Global BGP is not configured";
			}
			/* RD is mandatory to configure BGP under routing-instance */
			must "(../../route-distinguisher)" {
				error-message "Route Distinguisher is not configured on the Routing Instance";
			}
			/*
				'asnumber' will be a more meaningful name for the key field than
				'tagnode'. But protocol-bgp module has few groups which are reused here
				and those groups refer to this field as 'tagnode'. 'list bgp' key field
				is named as 'tagnode' in protocol-bgp module. We cannot change that name
				at present because it breaks backward compatibility.
			*/
			key "tagnode";
			leaf tagnode {
				description "BGP AS Number";
				type uint32 {
					range 1..max;
				}
				configd:help "Border Gateway Protocol (BGP) parameters";

				//ASN should be same as Global BGP
				must "(current() = /protocols:protocols/protocols-bgp:bgp/protocols-bgp:tagnode)" {
					error-message "AS Number must be same as the Global BGP";
				}
			}

			uses bgp-params-global-vrf;
			uses protocols-bgp:bgp-params-peer-group;
			uses protocols-bgp:bgp-params-neighbor {
				refine neighbor {
					configd:validate "/opt/vyatta/share/tmplscripts/protocols/bgp/neighbor/configd_validate_routing_instance.sh";
				}
			}
			uses protocols-bgp:bgp-params-address-family;
			uses bgp-params-vrf-log;
		}
	}

	/* BGP specific routing instance parameters */
	grouping bgp-routing-instance-params {
		leaf route-distinguisher {
			configd:priority "720";
			type rt-rd;
			description "Configure Route Distinguisher in ASN:NN or IPAddress:NN format";
			configd:update "/opt/vyatta/share/tmplscripts/protocols/bgp/config_rd.sh";
			configd:delete "/opt/vyatta/share/tmplscripts/protocols/bgp/config_rd.sh";
			configd:help "Route Distinguisher in ASN:NN or IPAddress:NN format";

			must "count(/routing-instance:routing/routing-instance:routing-instance[route-distinguisher = current()]) <= 1" {
				error-message "Route Distinguisher must be unique across the Routing Instances";
			}

			/* 4-byte ASN cannot be configured unless Ext ASN is configured.
			   Second condition is to relax the IP address */
			must "((substring-before(current(), ':') <= 65535) or (contains(substring-before(current(), ':'), '.')) or " +
				"(/protocols:protocols/protocols-bgp:bgp/protocols-bgp:parameters/protocols-bgp:extended-asn-capability))" {
				error-message "Extended ASN Capability must be enabled for configuring ASN greater than 65535";
			}
		}
		list route-target {
			configd:priority "720";
			description "Configure Route-Target in ASN:NN or IPAddress:NN format";
			configd:help "Route Target in ASN:NN or IPAddress:NN format";
			key "rt";
			leaf rt {
				type rt-rd;
				description "Configure Route-Target in ASN:NN or IPAddress:NN format";
				configd:help "Route-target"; 
			}
			leaf type {
				type enumeration {
					enum "import" {
						configd:help "import routes with this route-target";
						description "import routes with this route-target";
					}
					enum "export" {
						configd:help "export routes with this route-target";
						description "export routes with this route-target";
					}
					enum "both" {
						configd:help "export and import routes with this route-target";
						description "export and import routes with this route-target";
					}
				}
				mandatory true;
				description "Configure Route-Target Type";
				configd:help "Route-target type";
				configd:update "/opt/vyatta/share/tmplscripts/protocols/bgp/config_rt.sh";
				configd:delete "/opt/vyatta/share/tmplscripts/protocols/bgp/config_rt.sh";
			}
		}
	}

	/* Augmenting to protocols - routing-instance - VRF */
	augment /routing-instance:routing/routing-instance:routing-instance/routing-instance:protocols {
		uses bgp-routing-instance;
	}

	/* Augmenting to routing-instance - VRF */
	augment /routing-instance:routing/routing-instance:routing-instance {
		uses bgp-routing-instance-params;
	}

}
