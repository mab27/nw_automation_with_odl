module vyatta-interfaces-l2tpeth-v1 {
	namespace "urn:vyatta.com:mgmt:vyatta-interfaces-l2tpeth:1";
	prefix vyatta-interfaces-l2tpeth-v1;

	import vyatta-interfaces-v1 {
		prefix if;
	}
	import vyatta-interfaces-dataplane-v1 {
		prefix interfaces-dataplane;
	}
	import vyatta-types-v1 {
		prefix types;
	}
	import configd-v1 {
		prefix configd;
	}
	import vyatta-xconnect-v1 {
		prefix xconnect;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module for Layer 2 Tunnel Protocol Version 3 (L2TPv3)
		 interfaces.";

	revision 2016-05-04 {
		description "Add mandatory and range to l2tp-session";
	}
	revision 2016-03-28 {
		description "Remove use of bash in action scripts";
	}
	revision 2015-08-14 {
		description "Initial revision of version 1.";
	}

	augment /if:interfaces {
		list l2tpeth {
			configd:priority "500";
			configd:help "L2TPv3 static tunnel interface";
			configd:defer-actions "/opt/vyatta/sbin/vyatta-l2tpeth.pl ${COMMIT_ACTION} $VAR(@)";
			configd:end "/opt/vyatta/share/tmplscripts/interfaces/l2tpeth/configd_end.sh";
			key "tagnode";
			leaf tagnode {
				type string {
					pattern "lttp[0-9]+";
					configd:pattern-help "<lttpN>";
				}
				configd:help "L2TPv3 static tunnel interface";
			}
			leaf description {
				configd:priority "510";
				type string {
					pattern ".{1,256}" {
						error-message "interface description is too long (limit 256 characters)";
					}
				}
				configd:help "Description";
				configd:update "/opt/vyatta/share/tmplscripts/interfaces/l2tpeth/description/configd_update.sh";
				configd:delete "/opt/vyatta/share/tmplscripts/interfaces/l2tpeth/description/configd_delete.sh";
				configd:validate "/opt/vyatta/share/tmplscripts/interfaces/l2tpeth/description/configd_validate1.cli";
			}
			container ip {
				configd:help "IPv4 parameters";
				leaf enable-proxy-arp {
					configd:priority "510";
					type empty;
					configd:help "Enable proxy-arp on this interface";
					configd:create "/opt/vyatta/share/tmplscripts/interfaces/l2tpeth/ip/enable-proxy-arp/configd_create.sh";
					configd:delete "/opt/vyatta/share/tmplscripts/interfaces/l2tpeth/ip/enable-proxy-arp/configd_delete.sh";
				}
				leaf disable-forwarding {
					configd:priority "510";
					type empty;
					configd:help "Disable IPv4 forwarding on this interface";
					configd:create "/opt/vyatta/share/tmplscripts/interfaces/l2tpeth/ip/disable-forwarding/configd_create.sh";
					configd:delete "/opt/vyatta/share/tmplscripts/interfaces/l2tpeth/ip/disable-forwarding/configd_delete.sh";
				}
			}
			container ipv6 {
				presence "true";
				configd:help "IPv6 parameters";
			}
			leaf mtu {
				type uint32 {
					range 64..9000;
				}
				configd:priority "510";
				configd:help "Maximum Transmission Unit (MTU)";
				configd:create "/opt/vyatta/share/tmplscripts/interfaces/l2tpeth/mtu/configd_create.sh";
				configd:update "/opt/vyatta/share/tmplscripts/interfaces/l2tpeth/mtu/configd_update.sh";
				configd:delete "/opt/vyatta/share/tmplscripts/interfaces/l2tpeth/mtu/configd_delete.sh";
				configd:validate "/opt/vyatta/share/tmplscripts/interfaces/l2tpeth/mtu/configd_validate1.cli";
			}
			leaf disable {
				type empty;
				configd:priority "510";
				configd:help "Disable interface";
				configd:create "/opt/vyatta/share/tmplscripts/interfaces/l2tpeth/disable/configd_create.sh";
				configd:validate "/opt/vyatta/share/tmplscripts/interfaces/l2tpeth/disable/configd_validate1.cli";
			}
			list vif {
				configd:priority "510";
				configd:help "Virtual Interface (VIF) ID";
				configd:create "/opt/vyatta/share/tmplscripts/interfaces/l2tpeth/vif/configd_create.sh";
				configd:delete "/opt/vyatta/share/tmplscripts/interfaces/l2tpeth/vif/configd_delete.sh";
				configd:validate "/opt/vyatta/share/tmplscripts/interfaces/l2tpeth/vif/configd_validate1.cli";
				configd:validate "/opt/vyatta/share/tmplscripts/interfaces/l2tpeth/vif/configd_validate2.cli";
				configd:end "/opt/vyatta/sbin/vyatta-intf-end $VAR(../@).$VAR(@)";
				key "tagnode";
				leaf tagnode {
					type uint32 {
						range 1..4094;
					}
					configd:help "Virtual Interface (VIF) ID";
				}
				leaf vlan {
					type uint32 {
						range 1..4094;
					}
					configd:help "Virtual Local Area Network (VLAN) ID";
					configd:update "vyatta-interfaces.pl --dev $VAR(../../@) --update-vif $VAR(../@) --update-vlan";
					configd:delete "vyatta-interfaces.pl --dev $VAR(../../@) --update-vif $VAR(../@) --delete-vlan";
				}
				leaf description {
					type string;
					configd:help "Description";
					configd:update "/opt/vyatta/share/tmplscripts/interfaces/l2tpeth/vif/description/configd_update.sh";
					configd:delete "/opt/vyatta/share/tmplscripts/interfaces/l2tpeth/vif/description/configd_delete.sh";
				}
				container ip {
					configd:help "IPv4 parameters";
					leaf enable-proxy-arp {
						type empty;
						configd:help "Enable proxy-arp on this interface";
						configd:create "/opt/vyatta/share/tmplscripts/interfaces/l2tpeth/vif/ip/enable-proxy-arp/configd_create.sh";
						configd:delete "/opt/vyatta/share/tmplscripts/interfaces/l2tpeth/vif/ip/enable-proxy-arp/configd_delete.sh";
					}
				}
				container ipv6 {
					presence "true";
					configd:help "IPv6 parameters";
				}
				leaf mtu {
					type uint32 {
						range 68..9000;
					}
					configd:help "Maximum Transmission Unit (MTU)";
					configd:create "/opt/vyatta/share/tmplscripts/interfaces/l2tpeth/vif/mtu/configd_create.sh";
					configd:update "/opt/vyatta/share/tmplscripts/interfaces/l2tpeth/vif/mtu/configd_update.sh";
					configd:delete "/opt/vyatta/share/tmplscripts/interfaces/l2tpeth/vif/mtu/configd_delete.sh";
				}
				leaf disable {
					type empty;
					configd:help "Disable interface";
					configd:update "/opt/vyatta/share/tmplscripts/interfaces/l2tpeth/vif/disable/configd_update.sh";
				}
				leaf-list address {
					type if:address;
					ordered-by "user";
					configd:help "IP address";
					configd:create "/opt/vyatta/share/tmplscripts/interfaces/l2tpeth/vif/address/configd_create.sh";
				}
			}
			leaf-list address {
				type if:address;
				ordered-by "user";
				configd:priority "510";
				configd:help "IP address";
				configd:create "/opt/vyatta/share/tmplscripts/interfaces/l2tpeth/address/configd_create.sh";
				configd:validate "/opt/vyatta/share/tmplscripts/interfaces/l2tpeth/address/configd_validate1.cli";
			}
			container l2tp-session {
				configd:help "L2TPv3 static tunnel interface";
				configd:begin "/opt/vyatta/share/tmplscripts/interfaces/l2tpeth/l2tp-session/configd_begin.sh";
				configd:delete "/opt/vyatta/share/tmplscripts/interfaces/l2tpeth/l2tp-session/configd_delete.sh";
				configd:validate "/opt/vyatta/share/tmplscripts/interfaces/l2tpeth/l2tp-session/configd_validate.cli";
				leaf local-ip {
					type union {
						type types:ipv4-address;
						type types:ipv6-address;
					}
					configd:help "Local IP address for this tunnel";
					mandatory true;
				}
				leaf remote-cookie {
					type string {
						pattern "([0-9A-Fa-f]{8}|[0-9A-Fa-f]{16})" {
							error-message "Cookie must be 8 or 16 hex characters";
						}
						configd:pattern-help "<8 or 16 byte hex string (e.g. abcdef01)>";
					}
					configd:help "Optional remote cookie for this session";
				}
				leaf remote-udp-port {
					type uint32 {
						range 1..65535;
					}
					configd:help "Remote UDP port for this tunnel";
				}
				leaf local-cookie {
					type string {
						pattern "([0-9A-Fa-f]{8}|[0-9A-Fa-f]{16})" {
							error-message "Cookie must be 8 or 16 hex characters";
						}
						configd:pattern-help "<8 or 16 byte hex string (e.g. abcdef01)>";
					}
					configd:help "Optional local cookie for this session";
				}
				leaf local-udp-port {
					type uint32 {
						range 1..65535;
					}
					configd:help "Local UDP port for this tunnel";
				}
				leaf remote-ip {
					type union {
						type types:ipv4-address;
						type types:ipv6-address;
					}
					configd:help "Remote IP address for this tunnel";
					mandatory true;
				}
				leaf local-session-id {
					type uint32 {
						range 1..max;
					}
					must "(count(/if:interfaces/l2tpeth/l2tp-session[local-session-id = current()]) = 1)" {
						error-message "Local-session-id is already in use";
					}
					configd:help "Local session ID for this tunnel";
					mandatory true;
				}
				leaf encapsulation {
					type string;
					configd:help "Encapsulation of this tunnel interface";
					configd:allowed "/opt/vyatta/share/tmplscripts/interfaces/l2tpeth/l2tp-session/encapsulation/configd_allowed.sh";
					mandatory true;
				}
				leaf remote-session-id {
					type uint32 {
						range 1..max;
					}
					configd:help "Remote session ID for this tunnel";
					mandatory true;
				}
			}
		}
	}
	augment /if:interfaces/interfaces-dataplane:dataplane {
		uses xconnect:xconnect-if-binding;
	}

	augment /if:interfaces/interfaces-dataplane:dataplane/interfaces-dataplane:vif {
		uses xconnect:xconnect-if-binding {
		     	refine xconnect {
       		     	    configd:end "/opt/vyatta/share/tmplscripts/interfaces/dataplane/vif/xconnect/configd_end.sh";
       			    configd:validate "/opt/vyatta/share/tmplscripts/interfaces/dataplane/vif/xconnect/configd_validate.cli";
    			}
		}
	}
}
