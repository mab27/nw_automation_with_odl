module vyatta-ipv6-rtradv-v1 {
	namespace "urn:vyatta.com:mgmt:vyatta-ipv6-rtradv:1";
	prefix vyatta-ipv6-rtradv-v1;

	import vyatta-ipv6-rtradv-groups-v1 {
		prefix ipv6-rtradv-grp;
	}
	import vyatta-interfaces-v1 {
		prefix if;
	}
	import vyatta-interfaces-bridge-v1 {
		prefix interfaces-bridge;
	}
	import vyatta-interfaces-dataplane-v1 {
		prefix interfaces-dataplane;
	}
	import vyatta-interfaces-l2tpeth-v1 {
		prefix interfaces-l2tpeth;
	}
	import vyatta-interfaces-loopback-v1 {
		prefix interfaces-loopback;
	}
	import vyatta-interfaces-openvpn-v1 {
		prefix interfaces-openvpn;
	}
	import vyatta-interfaces-tunnel-v1 {
		prefix interfaces-tunnel;
	}
	import vyatta-interfaces-bonding-v1 {
		prefix interfaces-bonding;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module for vyatta-ipv6-rtradv-v1";

	revision 2017-03-08 {
		description "Allow IPv6 to be disabled for loopback interfaces";
	}

	revision 2016-09-08 {
		description "Reinstate prefix-lifetime, but mark it as obsolete";
	}

	revision 2016-09-01 {
		description "Migrate groupings and typedefs into a separate module
			(vyatta-ipv6-rtradv-groups-v1.yang)";
	}

	revision 2016-08-25 {
		description "Refactor groupings to support system (host) interfaces";
	}

	revision 2016-04-20 {
		description "Deprecate router-advert for loopback interfaces";
	}

	revision 2015-08-14 {
		description "Initial revision of version 1.";
	}

	typedef prefix-lifetime {
		status obsolete;
		type ipv6-rtradv-grp:prefix-lifetime;
	}

	augment /if:interfaces/interfaces-bridge:bridge/interfaces-bridge:ipv6 {
		uses ipv6-rtradv-grp:if-ipv6-parameters;
	}

	augment /if:interfaces/interfaces-dataplane:dataplane/interfaces-dataplane:ipv6 {
		uses ipv6-rtradv-grp:if-ipv6-parameters;
	}

	augment /if:interfaces/interfaces-dataplane:dataplane/interfaces-dataplane:vif/interfaces-dataplane:ipv6 {
		uses ipv6-rtradv-grp:vif-ipv6-parameters;
	}

	augment /if:interfaces/interfaces-l2tpeth:l2tpeth/interfaces-l2tpeth:ipv6 {
		uses ipv6-rtradv-grp:if-ipv6-parameters;
	}
	augment /if:interfaces/interfaces-l2tpeth:l2tpeth/interfaces-l2tpeth:vif/interfaces-l2tpeth:ipv6 {
		uses ipv6-rtradv-grp:vif-ipv6-parameters;
	}

	augment /if:interfaces/interfaces-loopback:loopback/interfaces-loopback:ipv6 {
		uses ipv6-rtradv-grp:if-disable-forwarding;
		uses ipv6-rtradv-grp:if-dup-addr-detect-transmits;
		uses ipv6-rtradv-grp:if-router-advert {
			status deprecated;
		}
		uses ipv6-rtradv-grp:if-address;
		uses ipv6-rtradv-grp:if-disable;
	}

	augment /if:interfaces/interfaces-openvpn:openvpn/interfaces-openvpn:ipv6 {
		uses ipv6-rtradv-grp:if-ipv6-parameters;
	}

	augment /if:interfaces/interfaces-tunnel:tunnel/interfaces-tunnel:ipv6 {
		uses ipv6-rtradv-grp:if-ipv6-parameters;
	}

	augment /if:interfaces/interfaces-bonding:bonding/interfaces-bonding:ipv6 {
		uses ipv6-rtradv-grp:if-ipv6-parameters;
	}

	augment /if:interfaces/interfaces-bonding:bonding/interfaces-bonding:vif/interfaces-bonding:ipv6 {
		uses ipv6-rtradv-grp:vif-ipv6-parameters;
	}
}
