module vyatta-service-flow-monitoring-dataplane-vif-v1 {
	namespace "urn:vyatta.com:mgmt:vyatta-service-flow-monitoring-dataplane-vif:1";
	prefix vyatta-service-flow-monitoring-dataplane-vif-v1;

	import configd-v1 {
		prefix configd;
	}
	import vyatta-interfaces-v1 {
		prefix if;
	}
	import vyatta-interfaces-dataplane-v1 {
		prefix if-dp;
	}
	import vyatta-service-flow-monitoring-v1 {
		prefix fm;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-service-flow-monitoring-dataplane-vif-v1";

	revision 2016-04-26 {
		description "Add Flow Monitoring support on dataplane VIF";
	}

	augment /if:interfaces/if-dp:dataplane/if-dp:vif {
		uses fm:interface-parameters {
			refine flow-monitoring/selector {
				configd:end "vplane-netflow.pl --intf=$VAR(../../../@) --type=$VAR(../../..) --vif=$VAR(../../@)";
			}
		}
	}
}
