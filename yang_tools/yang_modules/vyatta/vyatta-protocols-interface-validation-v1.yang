module vyatta-protocols-interface-validation-v1 {
	namespace "urn:vyatta.com:mgmt:vyatta-protocols-interface-validation:1";
	prefix vyatta-protocols-interface-validation-v1;

	import vyatta-interfaces-v1 {
		prefix if;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module package for vyatta-protocols-interface-validation-v1";
	
	revision 2016-07-21 {
		description "Removing peer-address grouping that was used by BGP,
			Move mpls interface out of common file,
			Remove RIP/RIPng specific groupings as the interface names
			used in RIP/RIPng no longer need to be validated against existing
			interfaces,
			Renaming of passive-interface and passive-interface-exclude 
			grouping of OSPF to IGP,
			Add mpls interface support";
	}
	
	revision 2016-01-21 {
		description "Initial revision of version 1";
	}


	grouping interface-common {
		leaf interface {
			type string;
			must "(current() = /if:interfaces/*/*[(local-name(.) = 'tagnode') or (local-name(.) = 'ifname')] "
				+ "or /if:interfaces/*/*[local-name(.) = 'vif'][./../* = substring-before(current(), '.')]"
				+ "/*[(local-name(.) = 'tagnode') or (local-name(.) = 'ifname')][. = substring-after(current(), '.')])" {
				error-message "Interface name must refer to an existing interface name";
			}
		}
	}

	grouping igp-passive-interface {
		leaf-list passive-interface {
			type union {
				type enumeration {
					enum "default";
				}
				type string;
			}
			configd:allowed "/opt/vyatta/sbin/vyatta-interfaces.pl --show all --filter-out ^ers";
			ordered-by "user";
			must "not( (current() = 'default') and (count(../passive-interface) > 1))" {
				error-message "Can't configure passive-interface 'default' with other interfaces";
			}
			must "current() = 'default' or (current() = /if:interfaces/*/*[(local-name(.) = 'tagnode') or (local-name(.) = 'ifname')] "
				+ "or /if:interfaces/*/*[local-name(.) = 'vif'][./../* = substring-before(current(), '.')]"
				+ "/*[(local-name(.) = 'tagnode') or (local-name(.) = 'ifname')][. = substring-after(current(), '.')])" {
				error-message "Invalid interface name";
			}
		}
	}

	grouping igp-passive-interface-exclude {
		leaf-list passive-interface-exclude {
			type string;
			configd:allowed "/opt/vyatta/sbin/vyatta-interfaces.pl --show all --filter-out ^ers";
			ordered-by "user";
			must "(../passive-interface = 'default')" {
				error-message "Can't configure passive-interface-exclude without configuring passive-interface 'default'";
			}
			must "(current() = /if:interfaces/*/*[(local-name(.) = 'tagnode') or (local-name(.) = 'ifname')] "
				+ "or /if:interfaces/*/*[local-name(.) = 'vif'][./../* = substring-before(current(), '.')]"
				+ "/*[(local-name(.) = 'tagnode') or (local-name(.) = 'ifname')][. = substring-after(current(), '.')])" {
				error-message "Invalid interface name";
			}
		}
	}
}
