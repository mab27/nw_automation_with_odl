module vyatta-interfaces-tunnel-v1 {
	namespace "urn:vyatta.com:mgmt:vyatta-interfaces-tunnel:1";
	prefix vyatta-interfaces-tunnel-v1;

	import vyatta-dscp-v1 {
		prefix dscp;
	}
	import vyatta-interfaces-v1 {
		prefix if;
	}
	import vyatta-types-v1 {
		prefix types;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2016-2017 by Brocade Communications Systems, Inc.
		 All rights reserved.

		 Tunnel interface configuration";

	revision 2017-01-13 {
		description "Change configd:update for ip key parameter and delete configd:create";
	}
	revision 2016-11-19 {
		description "Add tunnel disable config:end tmplscript";
	}
	revision 2016-10-28 {
		description "Add support - the local tunnel underlay interface
			can now be a DHCP addressed interface";
	}
	revision 2016-10-21 {
		description "Increase maximum allowed MTU on tunnel i/f.";
	}

	revision 2016-06-21 {
		description "Add mutual exclusion between Path MTU Discovery
			     and Ignore-DF.";
	}

	revision 2016-04-14 {
		description "Add GRE ignore DF feature.";
	}

	revision 2015-08-14 {
		description "Initial revision of version 1.";
	}

	augment /if:interfaces {
		list tunnel {
			configd:priority "380";
			configd:help "Tunnel interface";
			configd:defer-actions "/opt/vyatta/sbin/vyatta-tunnel-deferred.pl ${COMMIT_ACTION} $VAR(@)";
			configd:create "/opt/vyatta/share/tmplscripts/interfaces/tunnel/configd_create.sh";
			configd:delete "/opt/vyatta/share/tmplscripts/interfaces/tunnel/configd_delete.sh";
			configd:end "/opt/vyatta/share/tmplscripts/interfaces/tunnel/configd_end.sh";
			configd:validate "/opt/vyatta/share/tmplscripts/interfaces/tunnel/configd_validate1.cli";
			configd:validate "/opt/vyatta/share/tmplscripts/interfaces/tunnel/configd_validate2.cli";
			configd:validate "/opt/vyatta/share/tmplscripts/interfaces/tunnel/configd_validate3.cli";
			configd:validate "/opt/vyatta/share/tmplscripts/interfaces/tunnel/configd_validate4.cli";
			configd:validate "/opt/vyatta/share/tmplscripts/interfaces/tunnel/configd_validate5.cli";
			must "not(./parameters/ip/ignore-df) or ./path-mtu-discovery-disable" {
				error-message "Ignore DF can't be enabled while PMTU Discovery is enabled";
			}
			must "count(local-ip | local-interface)=1" {
				error-message "You must configure either local-ip or local-interface (but not both).";
			}
			key "tagnode";
			leaf tagnode {
				type string {
					length 4..15;
					pattern "tun[0-9]+";
					configd:pattern-help "<tunN>";
				}
				configd:help "Tunnel interface name";
			}
			container parameters {
				presence "true";
				configd:help "Tunnel parameters";
				container ip {
					presence "true";
					configd:help "IPv4 specific tunnel parameters";
					leaf ttl {
						type uint32 {
							range 0..255 {
								error-message "Must be between 0-255";
							}
						}
						configd:help "Time to live field";
						configd:update "/opt/vyatta/share/tmplscripts/interfaces/tunnel/parameters/ip/ttl/configd_update.sh";
						configd:delete "/opt/vyatta/share/tmplscripts/interfaces/tunnel/parameters/ip/ttl/configd_delete.sh";
						configd:validate "/opt/vyatta/share/tmplscripts/interfaces/tunnel/parameters/ip/ttl/configd_validate1.cli";
					}
					leaf key {
						type uint32 {
						    configd:syntax "/opt/vyatta/share/tmplscripts/interfaces/tunnel/parameters/ip/key/configd_syntax1.cli";
						}
						configd:help "Tunnel key";
						configd:validate "/opt/vyatta/share/tmplscripts/interfaces/tunnel/parameters/ip/key/configd_validate1.cli";
						configd:update "/opt/vyatta/share/tmplscripts/interfaces/tunnel/parameters/ip/key/configd_update.sh";
					}
					leaf tos {
						type union {
							type dscp:dscp-name;
							type enumeration {
								enum "inherit" {
									configd:help "Inherit from original IP header";
								}
							}
							type string {
								pattern "[0-9a-fA-F]{1,2}";
								configd:pattern-help "<0-FF>";
							}
						}
						configd:help "Type of Service (TOS)";
						default "inherit";
						configd:update "/opt/vyatta/share/tmplscripts/interfaces/tunnel/parameters/ip/tos/configd_update.sh";
						configd:delete "/opt/vyatta/share/tmplscripts/interfaces/tunnel/parameters/ip/tos/configd_delete.sh";
						configd:validate "/opt/vyatta/share/tmplscripts/interfaces/tunnel/parameters/ip/tos/configd_validate1.cli";
					}
					leaf ignore-df {
						type empty;
						description "Ignore DF bit when encapsulating.";
						configd:help "Ignore payload's DF bit when encapsulating.";
						configd:create "/opt/vyatta/share/tmplscripts/interfaces/tunnel/ignore-df/configd_create.sh";
						configd:delete "/opt/vyatta/share/tmplscripts/interfaces/tunnel/ignore-df/configd_delete.sh";
						must "../../../encapsulation = 'gre' or ../../../encapsulation = 'gre-multipoint'" {
							error-message "Only applicable to GRE layer 3 encapsulation.";
						}
					}
				}
				container ipv6 {
					presence "true";
					configd:help "IPv6 specific tunnel parameters";
					configd:delete "/opt/vyatta/share/tmplscripts/interfaces/tunnel/parameters/ipv6/configd_delete.sh";
					leaf tclass {
						type string {
							configd:syntax "/opt/vyatta/share/tmplscripts/interfaces/tunnel/parameters/ipv6/tclass/configd_syntax1.cli";
						}
						configd:help "Traffic class (Tclass)";
						default "0x00";
						configd:update "/opt/vyatta/share/tmplscripts/interfaces/tunnel/parameters/ipv6/tclass/configd_update.sh";
					}
					leaf hoplimit {
						type uint32 {
							range 0..255 {
								error-message "Must be between 0-255";
							}
						}
						configd:help "Hoplimit";
						default "64";
						configd:update "/opt/vyatta/share/tmplscripts/interfaces/tunnel/parameters/ipv6/hoplimit/configd_update.sh";
					}
					leaf encaplimit {
						type string {
							configd:syntax "/opt/vyatta/share/tmplscripts/interfaces/tunnel/parameters/ipv6/encaplimit/configd_syntax1.cli";
						}
						configd:help "Encaplimit field";
						default "4";
						configd:update "/opt/vyatta/share/tmplscripts/interfaces/tunnel/parameters/ipv6/encaplimit/configd_update.sh";
					}
					leaf flowlabel {
						type string {
							configd:syntax "/opt/vyatta/share/tmplscripts/interfaces/tunnel/parameters/ipv6/flowlabel/configd_syntax1.cli";
						}
						configd:help "Flowlabel";
						default "0x00000";
						configd:update "/opt/vyatta/share/tmplscripts/interfaces/tunnel/parameters/ipv6/flowlabel/configd_update.sh";
					}
				}
			}
			leaf local-ip {
				type union {
					type types:ipv4-address;
					type types:ipv6-address;
				}
				configd:help "Local IP address for this tunnel [either local-ip or local-interface is REQUIRED]";
				configd:update "/opt/vyatta/share/tmplscripts/interfaces/tunnel/local-interface/configd_update.sh";
			}
			leaf local-interface {
				type string;
				description "Allows DHCP Interface as local tunnel underlay interface in NHRP Spoke configurations (required)";
				must "(current() = /if:interfaces/*/*[(local-name(.) = 'tagnode') or (local-name(.) = 'ifname')] "
					+ "or /if:interfaces/*/*[local-name(.) = 'vif'][./../* = substring-before(current(), '.')]"
					+ "/*[(local-name(.) = 'tagnode') or (local-name(.) = 'ifname')][. = substring-after(current(), '.')])" {
					error-message "Interface name must refer to an existing (DHCP addressable) interface";
				}
				must "(/if:interfaces/*/*[((local-name(.) = 'tagnode') or (local-name(.) = 'ifname')) and (. = current())]/../*[(local-name(.) = 'address') and (. = 'dhcp')] "
				+ "or /if:interfaces/*/*[local-name(.) = 'vif'][./../* = substring-before(current(), '.')]"
                                + "/*[(local-name(.) = 'tagnode') or (local-name(.) = 'ifname')][. = substring-after(current(), '.')]/../*[(local-name(.) = 'address') and (. = 'dhcp')]/../*[(local-name(.) = 'address') and (. = 'dhcp')])" {
                                        error-message "Interface must have DHCP configured";
                                }
				configd:help "Underlay Interface that provides Local IP address for this NHRP Spoke tunnel (either local-ip or this is REQUIRED)";
				configd:update "/opt/vyatta/share/tmplscripts/interfaces/tunnel/local-interface/configd_update.sh";
			}
			leaf description {
				type string {
					pattern ".{1,256}" {
						error-message "interface description is too long (limit 256 characters)";
					}
				}
				configd:help "Description";
				configd:update "/opt/vyatta/share/tmplscripts/interfaces/tunnel/description/configd_update.sh";
				configd:delete "/opt/vyatta/share/tmplscripts/interfaces/tunnel/description/configd_delete.sh";
			}
			leaf mtu {
				type uint32 {
					range 68..16384;
				}
				configd:priority "381";
				configd:help "Maximum Transmission Unit (MTU)";
				configd:update "/opt/vyatta/share/tmplscripts/interfaces/tunnel/mtu/configd_update.sh";
				configd:delete "/opt/vyatta/share/tmplscripts/interfaces/tunnel/mtu/configd_delete.sh";
			}
			leaf multicast {
				type enumeration {
					enum "enable" {
						configd:help "Enable Multicast";
					}
					enum "disable" {
						configd:help "Disable Multicast (default)";
					}
				}
				configd:help "Multicast operation over tunnel";
				default "disable";
				configd:allowed "/opt/vyatta/share/tmplscripts/interfaces/tunnel/multicast/configd_allowed.sh";
				configd:update "/opt/vyatta/share/tmplscripts/interfaces/tunnel/multicast/configd_update.sh";
			}
			leaf path-mtu-discovery-disable {
				type empty;
				configd:help "Disable pmtu discovery support";
				configd:update "/opt/vyatta/share/tmplscripts/interfaces/tunnel/pmtudisc/configd_update.sh";
				configd:delete "/opt/vyatta/share/tmplscripts/interfaces/tunnel/pmtudisc/configd_delete.sh";
				configd:validate "/opt/vyatta/share/tmplscripts/interfaces/tunnel/pmtudisc/configd_validate1.sh";
			}
			leaf disable {
				type empty;
				configd:help "Disable interface";
				configd:create "/opt/vyatta/share/tmplscripts/interfaces/tunnel/disable/configd_create.sh";
				configd:delete "/opt/vyatta/share/tmplscripts/interfaces/tunnel/disable/configd_delete.sh";
				configd:end "/opt/vyatta/share/tmplscripts/interfaces/tunnel/disable/configd_end.sh";
			}
			leaf remote-ip {
				type union {
					type types:ipv4-address;
					type types:ipv6-address;
				}
				configd:help "Remote IP address for this tunnel";
				configd:update "/opt/vyatta/share/tmplscripts/interfaces/tunnel/remote-ip/configd_update.sh";
			}
			leaf-list address {
				type if:address;
				ordered-by "user";
				configd:help "IP address";
				configd:create "/opt/vyatta/share/tmplscripts/interfaces/tunnel/address/configd_create.sh";
			}
			leaf disable-link-detect {
				type empty;
				configd:help "Ignore link state changes";
				configd:create "/opt/vyatta/share/tmplscripts/interfaces/tunnel/disable-link-detect/configd_create.sh";
				configd:delete "/opt/vyatta/share/tmplscripts/interfaces/tunnel/disable-link-detect/configd_delete.sh";
			}
			leaf encapsulation {
				type enumeration {
					enum "gre" {
						configd:help "Generic Routing Encapsulation";
					}
					enum "gre-bridge" {
						configd:help "Generic Routing Encapsulation (for bridging)";
					}
					enum "gre-multipoint" {
						configd:help "Multipoint Generic Routing Encapsulation";
					}
					enum "ipip" {
						configd:help "IP in IP encapsulation";
					}
					enum "ipip6" {
						configd:help "IP in IPv6 encapsulation";
					}
					enum "ip6ip6" {
						configd:help "IPv6 in IPv6 encapsulation";
					}
					enum "sit" {
						configd:help "Simple Internet Transition encapsulation";
					}
				}
				configd:help "Encapsulation type";
				configd:create "/opt/vyatta/share/tmplscripts/interfaces/tunnel/encapsulation/configd_create1.cli";
				configd:update "/opt/vyatta/share/tmplscripts/interfaces/tunnel/encapsulation/configd_update1.cli";
			}
			container ip {
				configd:help "IPv4 parameters";
			}
			container ipv6 {
				presence "true";
				configd:help "IPv6 parameters";
			}
		}
	}
}
