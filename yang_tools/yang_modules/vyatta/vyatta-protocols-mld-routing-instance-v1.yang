module vyatta-protocols-mld-routing-instance-v1 {
	namespace "urn:vyatta.com:mgmt:vyatta-protocols-mld-routing-instance:1";
	prefix vyatta-protocols-mld-routing-instance-v1;

	import configd-v1 {
		prefix configd;
	}
	import vyatta-routing-v1 {
		prefix routing;
	}
	import vyatta-protocols-mld-v1 {
		prefix mld;
	}
	
	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-protocols-mld-routing-instance-v1";

	revision 2016-04-22 {
		description "Add routing-instance support for MLD
		augment routing/routinginstance/protocols";
	}

		augment /routing:routing/routing:routing-instance/routing:protocols {
		uses mld:mld-parameters {
			refine mld {
				configd:end "vyatta-igmp 6 --routing-instance $VAR(../../@)";
			}
		}
	}
}
