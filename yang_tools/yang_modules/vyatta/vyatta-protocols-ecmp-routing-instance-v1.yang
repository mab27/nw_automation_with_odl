module vyatta-protocols-ecmp-routing-instance-v1 {
	namespace "urn:vyatta.com:mgmt:vyatta-protocols-ecmp-routing-instance:1";
	prefix vyatta-protocols-ecmp-routing-instance-v1;

	import vyatta-protocols-ecmp-v1 {
		prefix vyatta-ecmp;
	}
	import vyatta-routing-v1 {
		prefix vyatta-routing;
	}	
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		All rights reserved.
		This module is to enable configuring max ecmp paths for a
		given routing-instance.";

	revision 2016-06-01 {
		description
			"This module is to enable configuring max ecmp paths for a
			given routing-instance."; 
	}

	augment /vyatta-routing:routing/vyatta-routing:routing-instance/vyatta-routing:protocols {
		container ecmp {
			configd:help "Equal-cost multi-path routing parameters for routing instance";
			description "Equal-cost multi-path routing parameters for routing instance";
			uses vyatta-ecmp:ecmp-paths; 
			uses vyatta-ecmp:disable; 
		}
	}
}
