module vyatta-protocols-pim6-routing-instance-v1 {
	namespace "urn:vyatta.com:mgmt:vyatta-protocols-pim6-routing-instance:1";
	prefix vyatta-protocols-pim6-routing-instance-v1;

	import configd-v1 {
		prefix configd;
	}
	import vyatta-routing-v1 {
		prefix routing;
	}
	import vyatta-protocols-pim6-v1 {
		prefix pim6;
	}
	import vyatta-routing-instance-interfaces-v1 {
		prefix rif;
	}

		organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-protocols-pim6-routing-instance-v1";

	revision 2016-04-26 {
		description "Augment /routing/routing-instance/protocols";
	}

	augment /routing:routing/routing:routing-instance/routing:protocols {
		uses pim6:pim6-parameters {
			refine pim6 {
				configd:end "vyatta-pim 6 --routing-instance $VAR(../../@)";
			}
			refine pim6/register-source/interface {
				must "current() = /routing:routing/routing:routing-instance" +
					"[routing:instance-name = current()/../../../../routing:instance-name]" +
					"/rif:interface/rif:name" {
					error-message "Interface must be configured in this routing instance";
				}
			}
			refine pim6/bsr-candidate/interface {
				must "current() = /routing:routing/routing:routing-instance" +
					"[routing:instance-name = current()/../../../../routing:instance-name]" +
					"/rif:interface/rif:name" {
					error-message "Interface must be configured in this routing instance";
				}
			}
			refine pim6/rp-candidate/interface {
				must "current()/tagnode = /routing:routing/routing:routing-instance" +
					"[routing:instance-name = current()/../../../../routing:instance-name]" +
					"/rif:interface/rif:name" {
					error-message "Interface must be configured in this routing instance";
				}
			}
		}
	}
}
