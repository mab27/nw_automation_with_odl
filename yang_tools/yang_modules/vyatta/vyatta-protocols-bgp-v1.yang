module vyatta-protocols-bgp-v1 {
	namespace "urn:vyatta.com:mgmt:vyatta-protocols-bgp:1";
	prefix vyatta-protocols-bgp-v1;

	import vyatta-types-v1 {
		prefix types;
	}
	import vyatta-protocols-v1 {
		prefix protocols;
	}
	import vyatta-services-v1 {
		prefix service;
	}
	import vyatta-service-snmp-v1 {
		prefix service-snmp;
	}
	import configd-v1 {
		prefix configd;
	}
	import vyatta-policy-v1 {
		prefix policy;
	}
	import vyatta-policy-route-v1 {
		prefix policy-route;
	}

	organization "Brocade Communications Systems, Inc.";
	contact
		"Brocade Communications Systems, Inc.
		 Postal: 130 Holger Way
		 San Jose, CA 95134
		 E-mail: support@Brocade.com
		 Web: www.brocade.com";

	description
		"Copyright (c) 2014-2016 by Brocade Communications Systems, Inc.
		 All rights reserved.

		 The YANG module package for vyatta-protocols-bgp-v1";

	revision 2016-10-26 {
		description
			"Support log option at neighbor level";
	}
	revision 2016-08-26 {
		description
			"Added an end statement for maximum-prefix list";
	}
	revision 2016-07-20 {
		description
			"Re-positioned Yang validation for global route-map export"+
			"Added validation for neighbor without remote-as and AFI"+
			"Removed few validations under 'ttl-security' and 'warning-only' nodes to ensure backwards compatibility"+
			"Removed validations for dampening parameters"+
			"Removed interface-validation Yang import"+
			"Adding few more validations to support peer-group configurations"+
			"Modified relative path to absolute path so that the paths are valid even in the imported Yang files"+
			"Adding more debug logs and grouping them as well"+
			"Config validations using relative path";
	}
	revision 2015-09-23 {
		description "Initial revision of version 1";
	}

	grouping route-map-group {
		leaf route-map {
			description "Route-map for filtering";
			configd:help "Route-map for filtering";
			type leafref {
				path "/policy:policy/policy-route:route/policy-route:route-map/policy-route:tagnode";
			}
		}
	}

	/* This grouping contains relative path to nodes outside the group scope. It can only be used
	   at a specific config level matching the relative path.
	*/
	grouping neighbor-route-map {
		container route-map {
			description "Route-map to filter route updates to/from this entity (neighbor or peer-group)";
			configd:help "Route-map to filter route updates to/from this entity (neighbor or peer-group)";
			leaf export {
				description "Route-map to filter outgoing route updates to this peer-group";
				type leafref {
					path "/policy:policy/policy-route:route/policy-route:route-map/policy-route:tagnode";
				}
				configd:help "Route-map to filter outgoing route updates to this peer-group";
			}
			leaf import {
				description "Route-map to filter incoming route updates from this entity (neighbor or peer-group)";
				type leafref {
					path "/policy:policy/policy-route:route/policy-route:route-map/policy-route:tagnode";
				}
				configd:help "Route-map to filter incoming route updates from this entity (neighbor or peer-group)";
			}
		}
	}
	grouping neighbor-vrrp-failover {
		list interface {
			description "This list is added to link the BGP VRRP group with interface VRRP group";
			max-elements "1";
			configd:help "VRRP Interface";
			configd:allowed "/opt/vyatta/sbin/vyatta-interfaces.pl --show all";
			key "ifname";
			leaf ifname {
				description "VRRP Interface Name";
				configd:help "VRRP Interface Name";
				type types:interface-ifname;
			}
			container vrrp-failover {
				description "Configure VRRP Failover Action";
				presence "VRRP Failover Action";
				configd:help "VRRP Failover";
				list vrrp-group {
					description "VRRP Group to associate the neighbor with";
					max-elements "1";
					configd:help "VRRP Group to associate the neighbor with";
					configd:create "${vyatta_sbindir}/vyatta-async-notify-bgp.pl $VAR(@) $VAR(../../@)";
					key "groupid";
					leaf groupid {
						description "VRRP Group ID";
						type uint8 {
							range 1..max;
						}
						configd:help "VRRP Group ID";
					}
					leaf prepend-as {
						description "Prepend AS Path for outbound routes while VRRP is backup";
						type string {
							pattern '[0-9]+( [0-9]+)*' {
								error-message "as-path should be string of numbers";
							}
							configd:syntax "/opt/vyatta/share/tmplscripts/protocols/bgp/peer-group/vrrp-failover/prepend-as/configd_syntax1.cli";
						}
						must "not(../med) and not(../route-map)" {
							error-message "You may set MED/prepend-as/route-map or none of them";
						}
						configd:help "Prepend AS Path";
					}
					leaf med {
						description "Set MED value for outbound routes while VRRP is backup";
						type uint32 {
							range 1..4294967294;
						}
						must "not(../prepend-as) and not(../route-map)" {
							error-message "You may set MED/prepend-as/route-map or none of them";
						}
						configd:help "Set MED value for outbound routes while VRRP is backup";
					}
					uses route-map-group {
						refine route-map {
							description "Route-map to modify route attributes while VRRP is backup";
							configd:help "Route-map to modify route attributes";
						}
					}
				}
			}
		}
	}
	/* This grouping contains relative path to nodes outside the group scope. It can only be used
	   at a specific config level matching the relative path.
	*/
	grouping neighbor-med-out {
		container med-out {
			description "Allow MED to be sent out";
			configd:help "Allow MED to be sent out";
			must "not(../address-family/*/peer-group)" {
				error-message "You may not configure med-out for a neighbor in peer-group\n";
			}
			container igp {
				description "Send MED based on IGP metric";
				presence "Enables med-out IGP";
				configd:help "Send MED based on IGP metric";
                		/* This and minimum-igp are mutually exclusive */
				leaf delay-updates {
					description "Delay updates of MED";
					type empty;
					configd:help "Delay updates of MED";
				}
			}
			leaf minimum-igp {
				description "Send MED based on minimal IGP metric";
				type empty;
				must "not(../igp)" {
					error-message "You can't set both 'med-out igp' and 'med-out minimum-igp'";
				}
				configd:help "Send MED based on minimal IGP metric";
			}
		}
	}
	/* This grouping contains relative path to nodes outside the group scope. It can only be used
	   at a specific config level matching the relative path.
	*/
	grouping neighbor-cluster-id {
		leaf cluster-id {
			description "Neighbor Cluster-id";
			configd:help "Neighbor Cluster-id";
			type union {
				type types:ipv4-address;
				type uint32 {
					range 1..max;
					configd:help "Neighbor Cluster-id as 32-bit number";
				}
			}
			must "(not(starts-with(current(), '127.')))" {
				error-message "Invalid cluster-id (cannot configure a loopback address) ";
			}
			must "(current() != '0.0.0.0')" {
				error-message "Invalid cluster-id (value cannot be 0.0.0.0)";
			}
			must "not(../remote-as) or (../remote-as) = (../../tagnode)" {
				error-message "Can not set both cluster-id and an eBGP remote-as";
			}
			must "not(../address-family/*/peer-group)" {
				error-message "You may not configure cluster-id for a neighbor in peer-group\n";
			}
		}
	}
	grouping ipv4-aggregate-address {
		list aggregate-address {
			description "BGP aggregate network";
			configd:help "BGP aggregate network";
			key "tagnode";
			leaf tagnode {
				description "BGP aggregate network";
				type types:ipv4-prefix {
					configd:normalize "normalize ipv4-prefix";
				}
				configd:help "BGP aggregate network";
			}
			leaf as-set {
				description "Generate AS-set path information for this aggregate address";
				type empty;
				configd:help "Generate AS-set path information for this aggregate address";
			}
			leaf summary-only {
				description "Announce the aggregate summary network only";
				type empty;
				configd:help "Announce the aggregate summary network only";
			}
		}
	}
	grouping ipv6-aggregate-address {
		list aggregate-address {
			description "BGP aggregate network";
			configd:help "BGP aggregate network";
			key "tagnode";
			leaf tagnode {
				description "IPv6 address";
				type types:ipv6-prefix {
					configd:normalize "normalize ipv6-prefix";
				}
				configd:help "BGP IPv6 aggregate network";
			}
			leaf as-set {
				description "Generate AS-set path information for this aggregate address";
				type empty;
				configd:help "Generate AS-set path information for this aggregate address";
			}
			leaf summary-only {
				description "Announce the aggregate summary network only";
				type empty;
				configd:help "Announce the aggregate summary network only";
			}
		}
	}

	grouping parameters-distance {
		container distance {
			description "Administrative distance for BGP routes";
			presence "Enables administrative distance for BGP routes";
			configd:help "Administrative distance for BGP routes";
			container global {
				description "Global administrative distances for BGP routes";
				presence "Enables global administrative distance for BGP";
				configd:help "Global administrative distances for BGP routes";
				leaf local {
					description "Administrative distance for local BGP routes";
					type uint32 {
						range 1..255;
					}
					configd:help "Administrative distance for local BGP routes";
					default "200";
				}
				leaf internal {
					description "Administrative distance for internal BGP routes";
					type uint32 {
						range 1..255;
					}
					configd:help "Administrative distance for internal BGP routes";
					default "200";
				}
				leaf external {
					description "Administrative distance for external BGP routes";
					type uint32 {
						range 1..255;
					}
					configd:help "Administrative distance for external BGP routes";
					default "20";
				}
			}
		}
	}
	grouping parameters-dampening {
		container dampening {
			description "Enable route-flap dampening";
			presence "Enables route-flap dampening";
			configd:help "Enable route-flap dampening";
			configd:validate "/opt/vyatta/share/tmplscripts/protocols/bgp/address-family/parameters/dampening/configd_validate.sh";

			leaf re-use {
				description "Penalty value to start reusing a route [REQUIRED]";
				type uint32 {
					range 1..20000;
				}
				default "750";
				configd:help "Penalty value to start reusing a route [REQUIRED]";
			}
			leaf half-life {
				description "Half-life time for dampening [REQUIRED]";
				type uint32 {
					range 1..45;
				}
				default "15";
				units minutes;
				configd:help "Half-life time for dampening [REQUIRED]";
			}
			leaf start-suppress {
				description "Penalty value to start suppressing a route [REQUIRED]";
				type uint32 {
					range 1..20000;
				}
				default "2000";
				configd:help "Penalty value to start suppressing a route [REQUIRED]";
			}
			leaf max-suppress-time {
				description "Maximum duration to suppress a stable route [REQUIRED]";
				type uint32 {
					range 1..255;
				}
				default "60";
				units minutes;
				configd:help "Maximum duration to suppress a stable route [REQUIRED]";
			}
			leaf un-reachability-half-life {
				description "Un-reachability half-life time for the penalty in minutes";
				type uint32 {
					range 1..45;
				}
				units minutes;
				configd:help "Un-reachability half-life time for the penalty in minutes";
			}
		}
	}

	grouping network-ipv4 {
		list network {
			description "BGP network";
			configd:help "BGP network";
			key "tagnode";
			leaf tagnode {
				description "BGP network";
				type types:ipv4-prefix {
					configd:normalize "normalize ipv4-prefix";
				}
				configd:help "BGP network";
			}
			leaf backdoor {
				description "Network as a backdoor route";
				type empty;
				configd:help "Network as a backdoor route";
			}
			uses route-map-group {
				refine route-map {
					must "not(../backdoor)" {
						error-message "You may configure route-map or backdoor, not both";
					}
					configd:help "Route-map to modify route attributes";
				}
			}
		}
	}

	grouping redistribute-ipv4 {
		container redistribute {
			description "Redistribute routes from other protocols into BGP";
			presence "Enables IPv4 redistribution";
			configd:help "Redistribute routes from other protocols into BGP";
			container kernel {
				description "Redistribute kernel routes into BGP";
				presence "Enables redistribution of kernel routes into BGP";
				configd:help "Redistribute kernel routes into BGP";
				uses route-map-group {
					refine route-map {
						configd:help "Route map to filter redistributed routes";
					}
				}
			}
			container rip {
				description "Redistribute RIP routes into BGP";
				presence "Enables redistribution of RIP routes into BGP";
				configd:help "Redistribute RIP routes into BGP";
				uses route-map-group {
					refine route-map {
						configd:help "Route map to filter redistributed routes";
					}
				}
			}
			container connected {
				description "Redistribute connected routes into BGP";
				presence "Enables redistribution of connected routes into BGP";
				configd:help "Redistribute connected routes into BGP";
				uses route-map-group {
					refine route-map {
						configd:help "Route map to filter redistributed routes";
					}
				}
			}
			container static {
				description "Redistribute static routes into BGP";
				presence "Enables redistribution of static routes into BGP";
				configd:help "Redistribute static routes into BGP";
				uses route-map-group {
					refine route-map {
						configd:help "Route map to filter redistributed routes";
					}
				}
			}
			container ospf {
				description "Redistribute OSPF routes into BGP";
				presence "Enables redistribution of OSPF routes into BGP";
				configd:help "Redistribute OSPF routes into BGP";
				uses route-map-group {
					refine route-map {
						configd:help "Route map to filter redistributed routes";
					}
				}
			}
		}
	}

	grouping network-ipv6 {
		list network {
			description "BGP IPv6 network";
			configd:help "BGP IPv6 network";
			key "tagnode";
			leaf tagnode {
				description "BGP IPv6 network";
				type types:ipv6-prefix {
					configd:normalize "normalize ipv6-prefix";
				}
				configd:help "BGP IPv6 network";
			}
			leaf backdoor {
				description "Network as a backdoor route";
				type empty;
				configd:help "Network as a backdoor route";
			}
			uses route-map-group {
				refine route-map {
					must "not(../backdoor)" {
						error-message "You may configure route-map or backdoor, not both!";
					}
					configd:help "Route-map to modify route attributes";
				}
			}
		}
	}

	grouping redistribute-ipv6 {
		container redistribute {
			description "Redistribute routes from other protocols into BGP";
			presence "Enables IPv6 Redistribution";
			configd:help "Redistribute routes from other protocols into BGP";
			container kernel {
				description "Redistribute kernel routes into BGP";
				presence "Enables redistribution of kernel routes into BGP";
				configd:help "Redistribute kernel routes into BGP";
				uses route-map-group {
					refine route-map {
						configd:help "Route map to filter redistributed routes";
					}
				}
			}
			container ripng {
				description "Redistribute RIP routes into BGP";
				presence "Enables redistribution of RIP routes into BGP";
				configd:help "Redistribute RIP routes into BGP";
				uses route-map-group {
					refine route-map {
						configd:help "Route map to filter redistributed routes";
					}
				}
			}
			container connected {
				description "Redistribute connected routes into BGP";
				presence "Enables redistribution of connected routes into BGP";
				configd:help "Redistribute connected routes into BGP";
				uses route-map-group {
					refine route-map {
						configd:help "Route map to filter redistributed routes";
					}
				}
			}
			container static {
				description "Redistribute static routes into BGP";
				presence "Enables redistribution of static routes into BGP";
				configd:help "Redistribute static routes into BGP";
				uses route-map-group {
					refine route-map {
						configd:help "Route map to filter redistributed routes";
					}
				}
			}
			container ospfv3 {
				description "Redistribute OSPF routes into BGP";
				presence "Enables redistribution of OSPF routes into BGP";
				configd:help "Redistribute OSPF routes into BGP";
				uses route-map-group {
					refine route-map {
						configd:help "Route map to filter redistributed routes";
					}
				}
			}
		}
	}

	/* This grouping contains relative path to nodes outside the group scope. It can only be used
	   at a specific config level matching the relative path.
	*/
	grouping neigh_peer_grp_ipv4_lists {
		container prefix-list {
			description "Prefix-list to filter route updates to/from this entity (neighbor or peer-group)";
			configd:help "Prefix-list to filter route updates to/from this entity (neighbor or peer-group)";
            		/* This and distribute-list are mutually exclusive */
			leaf export {
				description "Prefix-list to filter outgoing route updates to this peer-group";
				type leafref {
					path "/policy:policy/policy-route:route/policy-route:prefix-list/policy-route:tagnode";
				}
				configd:help "Prefix-list to filter outgoing route updates to this peer-group";
				must "not(../../peer-group)" {
					error-message "You may not configure prefix-list export for a neighbor in peer-group\n";
				}
			}
			leaf import {
				description "Prefix-list to filter incoming route updates from this peer-group";
				type leafref {
					path "/policy:policy/policy-route:route/policy-route:prefix-list/policy-route:tagnode";
				}
				configd:help "Prefix-list to filter incoming route updates from this peer-group";
			}
		}
		container distribute-list {
			description "Access-list to filter route updates to/from this entity (peer-group or neighbor)";
			configd:help "Access-list to filter route updates to/from this entity (peer-group or neighbor)";
			must "not(../prefix-list)" {
				error-message "You may not configure both prefix-list and distribute-list";
			}
			must "not(../peer-group)" {
				error-message "You may not configure distribute-list for a neighbor in peer-group\n";
			}
			leaf export {
				description "Access-list to filter outgoing route updates to this entity (peer-group or neighbor)";
				type uint32 {
					range 1..65535;
				}
				configd:help "Access-list to filter outgoing route updates to this entity (peer-group or neighbor)";
				configd:allowed "/opt/vyatta/share/tmplscripts/protocols/bgp/configd_allowed.sh distribute-list ipv4-unicast";
			}
			leaf import {
				description "Access-list to filter incoming route updates from this entity (peer-group or neighbor)";
				type uint32 {
					range 1..65535;
				}
				configd:help "Access-list to filter incoming route updates from this entity (peer-group or neighbor)";
				configd:allowed "/opt/vyatta/share/tmplscripts/protocols/bgp/configd_allowed.sh distribute-list ipv4-unicast";
			}
		}
	}

	/* This grouping contains relative path to nodes outside the group scope. It can only be used
	   at a specific config level matching the relative path.
	*/
	grouping neigh_peer_grp_ipv6_lists {
		container prefix-list {
			description "Prefix-list to filter route updates to/from this entity (neighbor or peer-group)";
			presence "Enables IPv6 prefix-list";
			configd:help "Prefix-list to filter route updates to/from this entity (neighbor or peer-group)";
			/* This and distribute-list are mutually exclusive */
			leaf export {
				description "Prefix-list to filter outgoing route updates to this peer-group";
				type leafref {
					path "/policy:policy/policy-route:route/policy-route:prefix-list6/policy-route:tagnode";
				}
				configd:help "Prefix-list to filter outgoing route updates to this peer-group";
				must "not(../../peer-group)" {
					error-message "You may not configure prefix-list export for a neighbor in peer-group\n";
				}
			}
			leaf import {
				description "Prefix-list to filter incoming route updates from this peer-group";
				type leafref {
					path "/policy:policy/policy-route:route/policy-route:prefix-list6/policy-route:tagnode";
				}
				configd:help "Prefix-list to filter incoming route updates from this peer-group";
			}
		}
		container distribute-list {
			description "Access-list to filter route updates to/from this entity (peer-group or neighbor)";
			presence "Enables IPv6 access-list";
			configd:help "Access-list to filter route updates to/from this entity (peer-group or neighbor)";
			must "not(../prefix-list)" {
				error-message "You may not configure both prefix-list and distribute-list";
			}
			must "not(../peer-group)" {
				error-message "You may not configure distribute-list for a neighbor in peer-group\n";
			}
			leaf export {
				description "Access-list to filter outgoing route updates to this entity (peer-group or neighbor)";
				type uint32 {
					range 1..65535;
				}
				configd:help "Access-list to filter outgoing route updates to this entity (peer-group or neighbor)";
				configd:allowed "/opt/vyatta/share/tmplscripts/protocols/bgp/configd_allowed.sh distribute-list ipv6-unicast";
			}
			leaf import {
				description "Access-list to filter incoming route updates from this entity (peer-group or neighbor)";
				type uint32 {
					range 1..65535;
				}
				configd:help "Access-list to filter incoming route updates from this entity (peer-group or neighbor)";
				configd:allowed "/opt/vyatta/share/tmplscripts/protocols/bgp/configd_allowed.sh distribute-list ipv6-unicast";
			}
		}
	}

	/* BGP Global parameters
	bgp <as-num> parameters
	   - extended-asn-capability
	   - no-rtm
	   - cluster-id <text>
	   - always-compare-med
	   - default local-pref <0-4294967295>
	   - confederation  (identifier <1-65535> | peer  <1-65535>)
	   - graceful-restart [graceful-reset | restart-time <1-3600> | stalepath-time <1-3600>]
	   - bestpath (as-path (confed | ignore) | compare-routerid |
	                med (confed | missing-as-worst))
	   - log-neighbor-changes
	   - no-fast-external-failover
	   - enforce-first-as
	   - scan-time <5-60>
	   - no-client-to-client-reflection
	   - deterministic-med
	   - maximum-paths (ebgp|ibgp) <2-64>
	   - router-id <x.x.x.x>
	*/

	grouping bgp-params-global-ext-asn-cap {
		leaf extended-asn-capability {
			description "Enable Extended ASN Capability (4 octet ASN)";
			type empty;
			configd:help "Enable Extended ASN Capability (4 octet ASN)";
		}
	}

	grouping bgp-params-global-no-rtm {
		leaf no-rtm {
			description "Prevent the installation of BGP learned routes into rtm";
			type empty;
			configd:help "Prevent the installation of BGP learned routes into rtm";
		}
	}

	grouping bgp-params-global-cluster-id {
		leaf cluster-id {
			description "Route-reflector cluster-id";
			type types:ipv4-address;
			must "(not(starts-with(current(), '127.')))" {
				error-message "Invalid cluster-id (cannot configure a loopback address) ";
			}
			must "(current() != '0.0.0.0')" {
				error-message "Invalid cluster-id (value cannot be 0.0.0.0)";
			}
			configd:help "Route-reflector cluster-id";
		}
	}

	grouping bgp-params-global-always-compare-med {
		leaf always-compare-med {
			description "Always compare MEDs from different neighbors";
			type empty;
			configd:help "Always compare MEDs from different neighbors";
		}
	}

	grouping bgp-params-global-default {
		container default {
			description "BGP defaults";
			presence "Enables BGP defaults";
			configd:help "BGP defaults";
			leaf local-pref {
				description "Default local preference (higher=more preferred)";
				type uint32;
				configd:help "Default local preference (higher=more preferred)";
			}
		}
	}

	grouping bgp-params-global-confederation-identifier {
		leaf identifier {
			description "Confederation AS identifier";
			type uint32 {
				range 1..max;
			}
			configd:help "Confederation AS identifier";
			must "((current() <=  65535) or " +
			"(/protocols:protocols/vyatta-protocols-bgp-v1:bgp/vyatta-protocols-bgp-v1:parameters/vyatta-protocols-bgp-v1:extended-asn-capability))" {
				error-message "Extended ASN Capability must be enabled for configuring ASN greater than 65535";
			}
		}
	}

	grouping bgp-params-global-confederation-peers {
		leaf-list peers {
			description "Peer ASes in the BGP confederation";
			type uint32 {
				range 1..max;
			}
			ordered-by "user";
			configd:help "Peer ASes in the BGP confederation";
			must "((current() <=  65535) or " +
			"(/protocols:protocols/vyatta-protocols-bgp-v1:bgp/vyatta-protocols-bgp-v1:parameters/vyatta-protocols-bgp-v1:extended-asn-capability))" {
				error-message "Extended ASN Capability must be enabled for configuring ASN greater than 65535";
			}
			must "(/protocols:protocols/vyatta-protocols-bgp-v1:bgp/vyatta-protocols-bgp-v1:parameters/" +
				"vyatta-protocols-bgp-v1:confederation/vyatta-protocols-bgp-v1:identifier)" {
				error-message "You must set the confederation identifier";
			}
			must "(current() != ../../../tagnode)" {
				error-message "Cannot set confederation peer ASN to local ASN";
			}
			configd:validate "/opt/vyatta/share/tmplscripts/protocols/bgp/parameters/confederation/peers/configd_update.cli";
		}
	}

	/* This grouping contains relative path to nodes outside the group scope. It can only be used
	   at a specific config level matching the relative path.
	*/
	grouping bgp-params-global-confederation {
		container confederation {
			description "AS confederation parameters";
			presence "BGP Confederation config";
			configd:help "AS confederation parameters";
			uses bgp-params-global-confederation-identifier;
			uses bgp-params-global-confederation-peers;
		} /*confederation*/
	}

	grouping bgp-params-global-graceful-restart {
		container graceful-restart {
			description "Graceful restart capability parameters";
			presence "Enables BGP Graceful-restart";
			configd:help "Graceful restart capability parameters";
			leaf graceful-reset {
				description "Enable graceful reset capability";
				type empty;
				configd:help "Enable graceful reset capability";
			}
			leaf restart-time {
				description "Max time needed for Neighbor(s) to restart";
				type uint32 {
					range 1..3600;
				}
				default "90";
				configd:help "Max time needed for Neighbor(s) to restart";
			}
			leaf stalepath-time {
				description "Maximum time to hold onto restarting peer's stale paths";
				type uint32 {
					range 1..3600;
				}
				default "360";
				configd:help "Maximum time to hold onto restarting peer's stale paths";
			}
		} /*graceful-restart*/
	}

	grouping bgp-params-global-bestpath {
		container bestpath {
			description "Default bestpath selection mechanism";
			presence "Enables bestpath selection mechanism";
			configd:help "Default bestpath selection mechanism";
			container med {
				description "MED attribute comparison parameters";
				presence "Enables MED attribute comparison";
				configd:help "MED attribute comparison parameters";
				container confed {
					description "Compare MEDs among confederation paths";
					presence "Compare MEDs among confederation paths";
					configd:help "Compare MEDs among confederation paths";
					leaf missing-as-worst {
						description "Treat missing route as a MED as the least preferred one";
						type empty;
						configd:help "Treat missing route as a MED as the least preferred one";
					}
				}
				leaf missing-as-worst {
					description "Treat missing route as a MED as the least preferred one";
					type empty;
					configd:help "Treat missing route as a MED as the least preferred one";
				}
			}
			container as-path {
				description "AS-path attribute comparison parameters";
				presence "Enables AS-path attribute comparison";
				configd:help "AS-path attribute comparison parameters";
				leaf ignore {
					description "Ignore AS-path length in selecting a route";
					type empty;
					configd:help "Ignore AS-path length in selecting a route";
				}
				leaf confed {
					description "Compare AS-path lengths including confederation sets & sequences";
					type empty;
					configd:help "Compare AS-path lengths including confederation sets & sequences";
				}
			}
			leaf compare-routerid {
				description "Compare the router-id for identical eBGP paths";
				type empty;
				configd:help "Compare the router-id for identical eBGP paths";
			}
			leaf igp-metric-ignore {
				description "Ignore IGP metric in BGP paths comparison";
				type empty;
				configd:help "Ignore IGP metric in BGP paths comparison";
			}
		} /*bestpath*/
	}

	grouping bgp-params-global-log-neighbor-changes {
		leaf log-neighbor-changes {
			description "Log neighbor up/down changes and reset reason";
			type empty;
			configd:help "Log neighbor up/down changes and reset reason";
		}
	}

	grouping bgp-params-global-no-fast-external-failover {
		leaf no-fast-external-failover {
			description "Disable immediate session reset if peer's connected link goes down";
			type empty;
			configd:help "Disable immediate session reset if peer's connected link goes down";
		}
	}

	grouping bgp-params-global-enforce-first-as {
		leaf enforce-first-as {
			description "Require first AS in the path to match peer's AS";
			type empty;
			configd:help "Require first AS in the path to match peer's AS";
		}
	}

	grouping bgp-params-global-scan-time {
		leaf scan-time {
			description "BGP route scanner interval";
			type uint32 {
				range 5..60;
			}
			configd:help "BGP route scanner interval";
		}
	}

	grouping bgp-params-global-maximum-as-limit {
		leaf maximum-as-limit {
			description "maximum-as-limit specifies maximum length of AS numbers in ASPATH or AS4PATH attribute";
			type uint8 {
				range 1..254;
			}
			configd:help "BGP maximum-as-limit for update message";
			default "254";
		}
	}

	grouping bgp-params-global-med-out-delay {
		leaf med-out-delay {
			description "Max time to defer MED updates";
			type uint32 {
				range 10..600;
			}
			configd:help "Max time to defer MED updates";
		}
	}

	grouping bgp-params-global-no-client-to-client-reflection {
		container no-client-to-client-reflection {
			description "Disable client to client route reflection";
			configd:help "Disable client to client route reflection";
			leaf all {
				description "Disable all client to client route reflection";
				type empty;
				configd:help "Disable all client to client route reflection";
			}
			leaf-list cluster-id {
				description "Configure intra-cluster reflection";
				configd:help "Configure intra-cluster reflection";
				type union {
					type types:ipv4-address;
					type enumeration {
						enum "any";
						configd:help "Configure intra-cluster reflection for any cluster id";
					}
				}
				must "(not(starts-with(current(), '127.')))" {
					error-message "Invalid cluster-id (cannot configure a loopback address) ";
				}
				must "(current() != '0.0.0.0')" {
					error-message "Invalid cluster-id (value cannot be 0.0.0.0)";
				}
			}
		}
	}

	grouping bgp-params-global-deterministic-med {
		leaf deterministic-med {
			description "Compare MEDs between different peers in the same AS";
			type empty;
			configd:help "Compare MEDs between different peers in the same AS";
		}
	}

	grouping bgp-params-global-maximum-paths {
		container maximum-paths {
			description "BGP multipaths";
			configd:help "BGP multipaths";
			leaf ibgp {
				description "Maximum iBGP multipaths";
				type uint32 {
					range 2..64;
				}
				configd:help "Maximum iBGP multipaths";
			}
			leaf ebgp {
				description "Maximum eBGP multipaths";
				type uint32 {
					range 2..64;
				}
				configd:help "Maximum eBGP multipaths";
			}
		}
	}

	grouping bgp-params-global-router-id {
		leaf router-id {
			description "BGP router id";
			type types:ipv4-address;
			must "(not((substring-before(., '.') >= 224) and " +
				"(substring-before(string(current()), '.') <= 239)))" {
				error-message "Invalid router-id (cannot be a multicast address)";
			}
			must "(not((substring-before(., '.') >= 240) and " +
				"(substring-before(string(current()), '.') <= 255)))" {
				error-message "Invalid router-id";
			}
			must "(not(starts-with(current(), '127.')))" {
				error-message "Invalid router-id (cannot configure a loopback address) ";
			}
			must "(current() != '0.0.0.0')" {
				error-message "Invalid router-id (value cannot be 0.0.0.0)";
			}
			configd:help "BGP router id";
		}
	}

	grouping bgp-params-timers {
		container timers {
			description "BGP protocol timers";
			presence "Enables BGP protocol timers";
			configd:help "BGP protocol timers";
			must "((holdtime = 0) or ((holdtime != 0) and (holdtime > keepalive)))" {
				error-message "Hold time can be 0; or should be greater than keepalive time";
			}
			leaf holdtime {
				description "BGP holdtime interval";
				type uint32 {
					range "0 | 3..65535";
				}
				configd:help "BGP holdtime interval";
				default "90";
			}
			leaf keepalive {
				description "Keepalive interval";
				type uint32 {
					range 0..65535;
				}
				default "30";
				configd:help "Keepalive interval";
			}
		}
	}

	grouping bgp-nexthop-rmap {
		container nexthop {
			description "This container specifies route-map to be applied on nexthop.";
			presence "Enables BGP nexthop";
			configd:help "BGP nexthop route-map filtering";
			uses route-map-group {
				refine route-map {
					description "This specifies route-map for bgp nexthop route filtering";
					configd:help "Route-map to select bgp nexthop";
				}
			}
		}
	}

	/*Peer-group and neighbor common settings (no families)
	   - advertisement-interval <0-65535>
	   - as-origination-interval <1-65535>
	   - capability dynamic
	   - capability route-refresh
	   - disable-capability-negotiation
	   - description <text>
	   - ebgp-multihop [ max-hop <1-255>]
	   - enforce-multihop
	   - local-as <1-4294967295>
	   - passive
	   - port <1-65535>
	   - remote-as <1-4294967295>
	   - shutdown
	   - timers (holdtime <0|3-65535>  keepalive <0-65535> | connect <1-65535>)
	   - ttl-security <1-255>
	   - update-source <text>
	   - override-capability
	   - password
	   - strict-capability-match
	   - vrrp-failover
	   - cluster-id*/
	/* This grouping contains relative path to nodes outside the group scope. It can only be used
	   at a specific config level matching the relative path.
	*/
	grouping peer-grp-neighbor-common-options {
		uses neighbor-vrrp-failover;
		uses neighbor-med-out;
		uses neighbor-cluster-id;
		leaf strict-capability-match {
			description "Enable strict capability negotiation";
			type empty;
			configd:help "Enable strict capability negotiation";
			must "not(../override-capability)" {
				error-message "You may not configure both strict-capability-match and override-capability";
			}
		}
		leaf password {
			description "BGP MD5 password";
			type string {
				length 1..80;
			}
			configd:secret "true";
			configd:help "BGP MD5 password";
		}
		leaf override-capability {
			description "Ignore capability negotiation with specified neighbor";
            		/* This and strict-capability-match are mutually exclusive */
			type empty;
			configd:help "Ignore capability negotiation with specified neighbor";
		}
		list local-as {
			max-elements "1";
			description "Local AS to allow customization of AS number";
			configd:help "Local AS to allow customization of AS number";
			key "tagnode";
			leaf tagnode {
				type uint32 {
					range 1..max;
				}
			}
			must "((tagnode <= 65535) or " +
                "(/protocols:protocols/vyatta-protocols-bgp-v1:bgp/vyatta-protocols-bgp-v1:parameters/vyatta-protocols-bgp-v1:extended-asn-capability))" {
				error-message "Extended ASN Capability must be enabled for configuring ASN greater than 65535";
			}
			must "not(../remote-as = ../../tagnode)" {
				error-message "You may not configure local-as for an iBGP neighbor/peer-group";
			}
			must "not(tagnode = ../../tagnode)" {
				error-message "You may not configure local-as the same as the true local AS";
			}
		}
		leaf as-origination-interval {
			description "Minimum interval between AS origination routing updates";
			type uint32 {
				range 1..65535;
			}
			configd:help "Minimum interval between AS origination routing updates";
		}
		container ttl-security {
			description "Ttl security mechanism for this entity (neighbor or peer-group)";
			presence "Enables TTL security";
			configd:help "Ttl security mechanism for this entity (neighbor or peer-group)";
			leaf hops {
				description "Number of the maximum number of hops to the BGP peer";
				type uint32 {
					range 1..254;
				}
				configd:help "Number of the maximum number of hops to the BGP peer";
			}
			must "not(../remote-as = ../../tagnode)" {
				error-message "You may not configure ttl-security for an iBGP neighbor/peer-group";
			}
		}
		container capability {
			description "Advertise capabilities to this entity (neighbor or peer-group)";
			presence "Enables BGP capabilities";
			configd:help "Advertise capabilities to this entity (neighbor or peer-group)";
			leaf dynamic {
				description "Advertise dynamic capability to this entity (neighbor or peer-group)";
				type empty;
				configd:help "Advertise dynamic capability to this entity (neighbor or peer-group)";
			}
			leaf route-refresh {
				description "Enable route-refresh capability advertisement for this entity (neighbor or peer-group)";
				type empty;
				configd:help "Enable route-refresh capability advertisement for this entity (neighbor or peer-group)";
			}
		}
		leaf disable-capability-negotiation {
			description "Disable capability negotiation with this entity (neighbor or peer-group)";
			type empty;
			configd:help "Disable capability negotiation with this entity (neighbor or peer-group)";
		}
		leaf enforce-multihop {
			description "Enforce multihop for eBGP neighbors";
			type empty;
			configd:help "Enforce multihop for eBGP neighbors";
			must "not(../remote-as = ../../tagnode)" {
				error-message "You may not configure enforce-multihop for an iBGP neighbor/peer-group";
			}
		}
		leaf description {
			description "Description for this entity (neighbor or peer-group)";
			type string {
				length 1..80;
			}
			configd:help "Description for this entity (neighbor or peer-group)";
		}
		leaf update-source {
			description "Source address or interface of routing updates";
			type union {
				type types:ipv4-address;
				type types:ipv6-address;
				type types:interface-ifname;
			}
			configd:help "Source address or interface of routing updates";
		}
		leaf advertisement-interval {
			description "Minimum interval for sending routing updates";
			type uint32 {
				range 0..65535;
			}
			configd:help "Minimum interval for sending routing updates";
		}
		leaf passive {
			description "Do not initiate a session with this entity (neighbor or peer-group)";
			type empty;
			configd:help "Do not initiate a session with this entity (neighbor or peer-group)";
		}
		leaf port {
			description "Neighbor's/Peer-group's BGP port";
			type uint32 {
				range 1..65535;
			}
			configd:help "Neighbor's/Peer-group's BGP port";
		}
		leaf shutdown {
			description "Administratively shut down neighbor";
			type empty;
			configd:help "Administratively shut down neighbor";
		}
		container timers {
			description "Neighbor/Peer-group timers";
			presence "Enables BGP timers";
			configd:help "Neighbor/Peer-group timers";
			must "((holdtime = 0) or ((holdtime != 0) and (holdtime > keepalive)))" {
				error-message "Hold time can be 0; or should be greater than keepalive time";
			}
			leaf connect {
				description "BGP connect timer for this entity (neighbor or peer-group)";
				type uint32 {
					range 1..65535;
				}
				configd:help "BGP connect timer for this entity (neighbor or peer-group)";
			}
			leaf holdtime {
				description "BGP hold timer for this entity (neighbor or peer-group)";
				type uint32 {
					range "0 | 3..65535";
				}
				default "90";
				configd:help "BGP hold timer for this entity (neighbor or peer-group)";
			}
			leaf keepalive {
				description "BGP keepalive interval for this neighbor";
				type uint32 {
					range 0..65535;
				}
				default "30";
				configd:help "BGP keepalive interval for this neighbor";
			}
		}
		leaf ebgp-multihop {
			description "Allow this eBGP neighbor to not be on a directly connected network";
			type uint32 {
				range 1..255;
			}
			configd:help "Allow this eBGP neighbor to not be on a directly connected network";
			must "not(../remote-as = ../../tagnode)" {
				error-message "You may not configure ebgp-multihop for an iBGP neighbor/peer-group";
			}
			must "not(../ttl-security)" {
				error-message "You may not configure both ttl-security hops and ebgp-multihop";
			}
		}
		leaf remote-as {
			description "BGP AS number of neighbor or peer-group";
			type uint32 {
				range 1..max;
			}
			must "((current() <=  65535) or " +
                "(/protocols:protocols/vyatta-protocols-bgp-v1:bgp/vyatta-protocols-bgp-v1:parameters/vyatta-protocols-bgp-v1:extended-asn-capability))" {
				error-message "Extended ASN Capability must be enabled for configuring ASN greater than 65535";
			}
			configd:help "Entity (peer-group or neighbor) BGP AS number [REQUIRED]";
		}
	}

	/*Peer-group & neighbor common parameters
	neighbor (<x.x.x.x>| <h:h:h:h:h:h:h:h>) | peer-group <text> [address-family (ipv4-unicast| ipv6-unicast)
	   - allowas-in [number <1-10>]
	   - attribute-unchanged [as-path]|[next-hop]|[med]
	   - filter-list (import <text> | export <text>)
	   - maximum-prefix <1-4294967295> [threshold | warning-only]
	   - remove-private-as
	   - route-reflector-client
	   - disable-send-community (extended | standard)
	   - weight <1-65535>
	   - capability graceful-restart
	   - route-map (import <text> | export <text>)
	   - default-originate [route-map <text>]
	   - soft-reconfiguration inbound
	   - unsuppress-map
	   - capability orf prefix-list (both|receive|send))
	   - route-server-client
	   - nexthop-self*/
	/*
       This grouping contains relative path to nodes outside the group scope.
       It can only be used at a specific config level matching the relative path.
       Also, there are few config nodes like 'route-reflector-client' which is
       referring to bgp AS number as 'tagnode'. So if this group has to be used in a
       bgp instance model, we have to make sure that the instance model uses 'tagnode'
       as the name for AS number. Please see comment in bgp routing-instance specific
       Yang file in this regard.
	*/
	grouping peer-grp-neighbor-afi-common-settings {
		uses neighbor-route-map;
		container filter-list {
			description "As-path-list to filter route updates to/from this entity (peer-group or neighbor)";
			presence "Enables applying as-path-list to filter route updates";
			configd:help "As-path-list to filter route updates to/from this entity (peer-group or neighbor)";
			leaf export {
				description "As-path-list to filter outgoing route updates to this entity (peer-group or neighbor)";
				type leafref {
					path "/policy:policy/policy-route:route/policy-route:as-path-list/policy-route:tagnode";
				}
				configd:help "As-path-list to filter outgoing route updates to this entity (peer-group or neighbor)";
			}
			leaf import {
				description "As-path-list to filter incoming route updates from this entity (peer-group or neighbor)";
				type leafref {
					path "/policy:policy/policy-route:route/policy-route:as-path-list/policy-route:tagnode";
				}
				configd:help "As-path-list to filter incoming route updates from this entity (peer-group or neighbor)";
			}
		}
		container attribute-unchanged {
			description "BGP attributes are sent unchanged";
			configd:help "BGP attributes are sent unchanged";
			leaf next-hop {
				description "Send nexthop unchanged";
				type empty;
				must "(../../../../ebgp-multihop)" {
					error-message "Nexthop unchanged can be configured only on multihop eBGP peers";
				}
				configd:help "Send nexthop unchanged";
			}
			leaf med {
				description "Send multi-exit discriminator unchanged";
				type empty;
				configd:help "Send multi-exit discriminator unchanged";
			}
			leaf as-path {
				description "Send AS path unchanged";
				type empty;
				configd:help "Send AS path unchanged";
			}
		}
		leaf remove-private-as {
			description "Remove private AS numbers from AS path in outbound route updates";
			type empty;
			configd:help "Remove private AS numbers from AS path in outbound route updates";
			must "not(../../../remote-as = ../../../../tagnode)" {
				error-message "You may not configure remove-private-as for an iBGP neighbor/peer-group";
			}
		}
		leaf route-reflector-client {
			description "Peer-group as a route reflector client";
			type empty;
			configd:help "Peer-group as a route reflector client";
			must "not(../../../remote-as) or (../../../remote-as) = (../../../../tagnode)" {
				error-message "You may not configure route-reflector-client for an eBGP neighbor/peer-group";
			}
		}
		list maximum-prefix {
			configd:priority "711";
			description "Maximum number of prefixes to accept from this entity (neighbor or peer-group)";
			max-elements "1";
			configd:help "Maximum number of prefixes to accept from this entity (neighbor or peer-group)";
			configd:end "/opt/vyatta/share/tmplscripts/protocols/bgp/peer-grp-neigh/address-family/maximum-prefix/configd_end.sh";
			key "tagnode";
			leaf tagnode {
				description "Maximum number of prefixes to accept from this entity (neighbor or peer-group)";
				type uint32 {
					range 1..max;
				}
				configd:help "Maximum number of prefixes to accept from this entity (neighbor or peer-group)";
			}
			leaf warning-only {
				description "Only give warning message when limit is exceeded";
				type empty;
				configd:help "Only give warning message when limit is exceeded";
				configd:validate "/opt/vyatta/share/tmplscripts/protocols/bgp/peer-grp-neigh/address-family/maximum-prefix/warning-only/configd_validate.cli";
			}
			list threshold {
				description "Threshold value (percentage) at which to generate a warning msg";
				max-elements "1";
				configd:help "Threshold value (percentage) at which to generate a warning msg";
				key "tagnode";
				leaf tagnode {
					description "Threshold value (percentage) at which to generate a warning msg";
					type uint32 {
						range 1..100;
					}
					configd:help "Threshold value (percentage) at which to generate a warning msg";
				}
				leaf warning-only {
					description "Only give warning message when limit is exceeded";
					type empty;
					configd:help "Only give warning message when limit is exceeded";
				}
			}
		}
		container allowas-in {
			description "Accept a route that contains the local-AS in the as-path";
			presence "Enables allowas-in feature";
			configd:help "Accept a route that contains the local-AS in the as-path";
			leaf number {
				description "Number of occurrences of AS number";
				type uint32 {
					range 1..10;
				}
				configd:help "Number of occurrences of AS number";
			}
		}

		leaf weight {
			description "Default weight for routes from this entity (neighbor or peer-group)";
			type uint32 {
				range 1..65535;
			}
			configd:help "Default weight for routes from this entity (neighbor or peer-group)";
		}

		container disable-send-community {
			description "Disable sending community attributes to this peer-group";
			configd:help "Disable sending community attributes to this peer-group";
			leaf extended {
				description "Disable sending extended community attributes to this entity (neighbor or peer-group)";
				type empty;
				configd:help "Disable sending extended community attributes to this entity (neighbor or peer-group)";
			}
			leaf standard {
				description "Disable sending standard community attributes to this entity (neighbor or peer-group)";
				type empty;
				configd:help "Disable sending standard community attributes to this entity (neighbor or peer-group)";
			}
		}

		container capability {
			description "Advertise capabilities to this entity (neighbor or peer-group)";
			presence "Enables BGP neighbor/peer-group AFI capabilities";
			configd:help "Advertise capabilities to this entity (neighbor or peer-group)";
			container graceful-restart {
				description "Advertise the graceful-restart capability to this entity (neighbor or peer-group)";
				presence "Enables graceful-restart capability at neighbor/peer-group AFI level";
				configd:help "Advertise the graceful-restart capability to this entity (neighbor or peer-group)";
				must "not(../../peer-group)" {
					error-message "You can't set graceful-restart for a neighbor in a peer-group. You must set it in the peer-group.";
				}
				leaf disable {
					description "Disable the advertisement of the graceful-restart capability to this entity (neighbor or peer-group)";
					type empty;
					configd:help "Disable the advertisement of the graceful-restart capability to this entity (neighbor or peer-group)";
				}
			}
			container orf {
				description "Advertise ORF capability to this neighbor";
				presence "Enables ORF capability at neighbor/peer-group AFI level";
				configd:help "Advertise ORF capability to this neighbor";
				container prefix-list {
					description "Advertise prefix-list ORF capability to this entity (neighbor or peer-group)";
					presence "Enables advertising prefix-list ORF capability";
					configd:help "Advertise prefix-list ORF capability to this entity (neighbor or peer-group)";
					leaf receive {
						description "Capability to receive the ORF";
						type empty;
						configd:help "Capability to receive the ORF";
					}
					leaf send {
						description "Capability to send the ORF";
						type empty;
						configd:help "Capability to send the ORF";
					}
				}
			}
		}

		container soft-reconfiguration {
			description "Soft reconfiguration for neighbor";
			configd:help "Soft reconfiguration for neighbor";
			leaf inbound {
				description "Inbound soft reconfiguration for this entity (neighbor or peer-group) [REQUIRED]";
				type empty;
				configd:help "Inbound soft reconfiguration for this entity (neighbor or peer-group) [REQUIRED]";
			}
		}

		container default-originate {
			description "Send default route to this neighbor";
			presence "Enables default-originate at neighbor/peer-group AFI level";
			configd:help "Send default route to this neighbor";
			uses route-map-group {
				refine route-map {
					configd:help "Route-map to specify criteria of the default";
				}
			}
		}

		leaf unsuppress-map {
			description "Route-map to selectively unsuppress suppressed routes";
			type leafref {
				path "/policy:policy/policy-route:route/policy-route:route-map/policy-route:tagnode";
			}
			configd:help "Route-map to selectively unsuppress suppressed routes";
		}

		leaf nexthop-self {
			description "Nexthop for routes sent to this peer-group to be the local router";
			type empty;
			configd:help "Nexthop for routes sent to this peer-group to be the local router";
		}

		leaf route-server-client {
			description "Peer-group as route server client";
			type empty;
			configd:help "Peer-group as route server client";
		}
	}

	/* BGP Global parameters supported under default VRF */
	grouping bgp-params-global-default-vrf {
		container parameters {
			description "BGP Global parameters that can be configured under Default BGP Routing Instance";
			presence "Enables BGP parameters";
			configd:help "BGP parameters";
			uses bgp-params-global-ext-asn-cap;
			uses bgp-params-global-no-rtm;
			uses bgp-params-global-cluster-id;
			uses bgp-params-global-always-compare-med;
			uses bgp-params-global-default;
			uses bgp-params-global-confederation;
			uses bgp-params-global-graceful-restart;
			uses bgp-params-global-bestpath;
			uses bgp-params-global-log-neighbor-changes;
			uses bgp-params-global-no-fast-external-failover;
			uses bgp-params-global-enforce-first-as;
			uses bgp-params-global-scan-time;
			uses bgp-params-global-maximum-as-limit;
			uses bgp-params-global-med-out-delay;
			uses bgp-params-global-no-client-to-client-reflection;
			uses bgp-params-global-deterministic-med;
			uses bgp-params-global-maximum-paths;
			uses bgp-params-global-router-id;
		}
		uses bgp-params-timers;
	}


	grouping bgp-params-peer-group {
			list peer-group {
				description "BGP Peer-group parameters";
				configd:help "BGP peer-group";
				key "tagnode";
				leaf tagnode {
					description "BGP peer-group";
					type string;
					configd:help "BGP peer-group";
				}
				uses peer-grp-neighbor-common-options {
					refine local-as {
						must "../../neighbor[address-family/*/peer-group = current()/../tagnode]/remote-as != ../../tagnode" {
							error-message "You may not configure local-as for a peer-group with iBGP member";
						}
						must "not(../../neighbor[address-family/*/peer-group = current()/../tagnode]/remote-as = current())" {
							error-message "You may not configure local-as the same as a member's remote-as";
						}
					}
					refine ttl-security {
						must "../../neighbor[address-family/*/peer-group = current()/../tagnode]/remote-as != ../../tagnode" {
							error-message "You may not configure ttl-security for a peer-group with iBGP member";
						}
					}
					refine enforce-multihop {
						must " ../../neighbor[address-family/*/peer-group = current()/../tagnode]/remote-as != ../../tagnode" {
							error-message "You may not configure enforce-multihop for a peer-group with iBGP member";
						}
					}
					refine ebgp-multihop {
						must "../../neighbor[address-family/*/peer-group = current()/../tagnode]/remote-as != ../../tagnode" {
							error-message "You may not configure ebgp-multihop for a peer-group with iBGP member";
						}
					}
					refine cluster-id {
						must "not (../../neighbor[address-family/*/peer-group = current()/../tagnode]/remote-as) or " +
							"(../../neighbor[address-family/*/peer-group = current()/../tagnode]/remote-as = ../../tagnode)" {
							error-message "You may not configure cluster-id for a peer-group with eBGP member";
						}
					}
				}
				container address-family {
					description "BGP peer-group address-family parameters";
					presence "Enables BGP peer-group address-family";
					configd:help "BGP peer-group address-family parameters";
					container ipv4-unicast {
						description "BGP peer-group IPv4 unicast parameters";
						presence "Enables BGP peer-group IPv4 unicast parameters";
						configd:help "BGP peer-group IPv4 unicast parameters";
						uses peer-grp-neighbor-afi-common-settings {
							refine remove-private-as {
								must "../../../../neighbor[address-family/*/peer-group = current()/../../../tagnode]/remote-as "+
									 " != ../../../../../bgp/tagnode" {
									 error-message "You may not configure remove-private-as for a peer-group with iBGP member";
								}
							}
							refine route-reflector-client {
								must "not (../../../../neighbor[address-family/*/peer-group = current()/../../../tagnode]/remote-as) or "+
									"(../../../../neighbor[address-family/*/peer-group = current()/../../../tagnode]/remote-as "+
									" = ../../../../../bgp/tagnode)" {
									error-message "You may not configure route-reflector-client for a peer-group with eBGP member";
								}
							}
						}
						uses neigh_peer_grp_ipv4_lists;
					}
					container ipv6-unicast {
						description "BGP peer-group IPv6 unicast parameters";
						presence "Enables BGP peer-group IPv6 unicast parameters";
						configd:help "BGP peer-group IPv6 unicast parameters";
						uses peer-grp-neighbor-afi-common-settings {
							refine remove-private-as {
								must "../../../../neighbor[address-family/*/peer-group = current()/../../../tagnode]/remote-as "+
									 " != ../../../../../bgp/tagnode" {
									 error-message "You may not configure remove-private-as for a peer-group with iBGP member";
								}
							}
							refine route-reflector-client {
								must "not (../../../../neighbor[address-family/*/peer-group = current()/../../../tagnode]/remote-as) or "+
									"(../../../../neighbor[address-family/*/peer-group = current()/../../../tagnode]/remote-as "+
									" = ../../../../../bgp/tagnode)" {
									error-message "You may not configure route-reflector-client for a peer-group with eBGP member";
								}
							}
						}
						uses neigh_peer_grp_ipv6_lists;
					}
				}
				must "not((cluster-id or (address-family/*/route-reflector-client)) and" +
				     "    (ebgp-multihop or enforce-multihop or ttl-security or local-as or (address-family/*/remove-private-as)))" {
					error-message "You may not configure both eBGP and iBGP type parameters";
				}
			}
	}

	/* Neighbor adddress grouping - validation scripts to be added during refine */
	grouping peer-address {
		leaf tagnode {
			type union {
				type types:ipv4-address;
				type types:ipv6-address;
			}
			configd:help "BGP neighbor";
			must "not((starts-with(current(), 'fe8')) or (starts-with(current(), 'fe9')) or " +
				  "(starts-with(current(), 'fea')) or (starts-with(current(), 'feb'))) or " +
				 "(../update-source) or " +
				 "(../../peer-group[tagnode = current()/../address-family/*/peer-group]/update-source)" {
				 error-message "You must configure update-source for IPv6 link-local neighbors\n";
			}
			must "not((starts-with(current(), 'fe8')) or (starts-with(current(), 'fe9')) or " +
				  "(starts-with(current(), 'fea')) or (starts-with(current(), 'feb'))) or " +
				 "(not(../ebgp-multihop) and " +
				 " not(../../peer-group[tagnode = current()/../address-family/*/peer-group]/ebgp-multihop))" {
				 error-message "You may not configure ebgp-multihop for IPv6 link-local neighbor\n";
			}
			must "not((starts-with(current(), 'fe8')) or (starts-with(current(), 'fe9')) or " +
				  "(starts-with(current(), 'fea')) or (starts-with(current(), 'feb'))) or " +
				 "(not(../ttl-security) and " +
				 " not(../../peer-group[tagnode = current()/../address-family/*/peer-group]/ttl-security))" {
				 error-message "You may not configure ttl-security for IPv6 link-local neighbor\n";
			}
		}
	}

	grouping bgp-params-log-all {
		leaf all {
			description "Enable all BGP logs";
			type empty;
			configd:help "Enable all BGP logs";
		}
	}
	grouping bgp-params-log-events {
		leaf events {
			description "Enable BGP events logs";
			type empty;
			configd:help "Enable BGP events logs";
		}
	}
	grouping bgp-params-log-filters {
		leaf filters {
			description "Enable BGP filters logs";
			type empty;
			configd:help "Enable BGP filters logs";
		}
	}
	grouping bgp-params-log-fsm {
		leaf fsm {
			description "Enable BGP fsm logs";
			type empty;
			configd:help "Enable BGP fsm logs";
		}
	}
	grouping bgp-params-log-nsm {
		leaf nsm {
			description "Enable BGP nsm logs";
			type empty;
			configd:help "Enable BGP nsm logs";
		}
	}
	grouping bgp-params-log-keepalive {
		leaf keepalive {
			description "Enable BGP keepalive logs";
			type empty;
			configd:help "Enable BGP keepalive logs";
		}
	}
	grouping bgp-params-log-update {
		container update  {
			description "BGP update logs";
			configd:help "BGP update logs";
			leaf in {
				description "Enable BGP update in logs";
				type empty;
				configd:help "Enable BGP update in logs";
			}
			leaf out {
				description "Enable BGP update out logs";
				type empty;
				configd:help "Enable BGP update out logs";
			}
			leaf all {
				description "Enable BGP update all logs";
				type empty;
				configd:help "Enable BGP update all logs";
			}
		}
	}
	grouping bgp-params-log-bfd {
		leaf bfd {
			description "Enable BGP BFD logs";
			type empty;
			configd:help "Enable BGP BFD logs";
		}
	}
	grouping bgp-params-log-dampening {
		leaf dampening {
			description "Enable BGP dampening logs";
			type empty;
			configd:help "Enable BGP dampening logs";
		}
	}
	grouping bgp-params-log-msdp {
		leaf msdp {
			description "Enable BGP msdp logs";
			type empty;
			configd:help "Enable BGP msdp logs";
		}
	}
	grouping bgp-params-log-rib {
		leaf rib {
			description "Enable BGP rib logs";
			type empty;
			configd:help "Enable BGP rib logs";
		}
	}

	grouping bgp-params-log {
		container log {
			description "BGP logging configuration parameters";
			configd:help "BGP logging parameters";
			uses bgp-params-log-all;
			uses bgp-params-log-events;
			uses bgp-params-log-filters;
			uses bgp-params-log-fsm;
			uses bgp-params-log-nsm;
			uses bgp-params-log-keepalive;
			uses bgp-params-log-update;
			uses bgp-params-log-bfd;
			uses bgp-params-log-dampening;
			uses bgp-params-log-msdp;
			uses bgp-params-log-rib;
		}
	}

	grouping bgp-params-neighbor-log {
		container log {
			description "BGP logging configuration parameters";
			configd:help "BGP logging parameters";
			uses bgp-params-log-all;
			uses bgp-params-log-events;
			uses bgp-params-log-filters;
			uses bgp-params-log-fsm;
			uses bgp-params-log-keepalive;
			uses bgp-params-log-update;
			uses bgp-params-log-bfd;
			uses bgp-params-log-dampening;
			uses bgp-params-log-msdp;
		}
	}
	/* This grouping contains relative path to nodes outside the group scope. It can only be used
	   at a specific config level matching the relative path.
	*/
	grouping bgp-params-neighbor {
			list neighbor {
				description "BGP neighbor level configuration parameters";
				configd:help "BGP neighbor";
				key "tagnode";
				uses peer-address;
				uses peer-grp-neighbor-common-options {
					refine strict-capability-match {
						must "not(../../peer-group[tagnode = current()/../address-family/*/peer-group]/override-capability)" {
							error-message "You may not configure strict-capability-match when override-capability is set in peer-group";
						}
					}
					refine override-capability {
						must "not(../../peer-group[tagnode = current()/../address-family/*/peer-group]/strict-capability-match)" {
							error-message "You may not configure override-capability when strict-capability-match is set in peer-group";
						}
					}
					refine local-as {
						must "not(../address-family/*/peer-group)" {
							error-message "You may not configure local-as for a neighbor in peer-group\n";
						}
					}
					refine as-origination-interval {
						must "not(../address-family/*/peer-group)" {
							error-message "You may not configure as-origination-interval for a neighbor in peer-group\n";
						}
					}
					refine ttl-security {
						must "not(../address-family/*/peer-group) or " +
							 "(../../peer-group[tagnode = current()/../address-family/*/peer-group]/remote-as != ../../tagnode)" {
							error-message "You may not configure ttl-security for a neighbor in iBGP peer-group";
						}
						must "not(../../peer-group[tagnode = current()/../address-family/*/peer-group]/ebgp-multihop) or " +
							 "((../../peer-group[tagnode = current()/../address-family/*/peer-group]/ebgp-multihop) = 1)" {
							error-message "You may not configure ttl-security hop when ebgp-multihop is set in peer-group";
						}
					}
					refine enforce-multihop {
						must "not(../address-family/*/peer-group) or " +
							 "(../../peer-group[tagnode = current()/../address-family/*/peer-group]/remote-as != ../../tagnode)" {
							error-message "You may not configure enforce-multihop for a neighbor in an iBGP peer-group";
						}
					}
					refine port {
						must "not(../address-family/*/peer-group)" {
							error-message "You may not configure port for a neighbor in peer-group\n";
						}
					}
					refine timers {
						must "not(../address-family/*/peer-group)" {
							error-message "You may not configure timer for a neighbor in peer-group\n";
						}
					}
					refine ebgp-multihop {
						must "(../../peer-group[tagnode = current()/../address-family/*/peer-group]/remote-as != ../../tagnode)" {
							error-message "You may not configure ebgp-multihop for a neighbor in an iBGP peer-group";
						}
						must "not(../../peer-group[tagnode = current()/../address-family/*/peer-group]/ttl-security)" {
							error-message "You may not configure ebgp-multihop when ttl-security hop is set in peer-group";
						}
					}
					refine remote-as {
						must "not(current()/../address-family/*/peer-group) or " +
							"(   (" +
									"(current() = ../../tagnode) and " +
									"not(../../neighbor[address-family/*/peer-group = current()/../address-family/*/peer-group]/remote-as != ../../tagnode)" +
								") or " +
								"(" +
									"(current() != ../../tagnode) and " +
									"not(../../neighbor[address-family/*/peer-group = current()/../address-family/*/peer-group]/remote-as = ../../tagnode)" +
								")" +
							")" {
							error-message "All members of a peer-group must be either iBGP or eBGP";
						}
					}
				}
				must "(not(address-family) or remote-as or (../peer-group[tagnode = current()/address-family/*/peer-group]/remote-as))" {
					error-message "remote-as must be configured either in neighbor or in peer-group";
				}
				must "not(remote-as and (../peer-group[tagnode = current()/address-family/*/peer-group]/remote-as))" {
					error-message "You may not configure remote-as both in neighbor and peer-group";
				}
				uses bgp-params-neighbor-log;
				uses neighbor-route-map {
					refine route-map/export {
						must "not(../../address-family/*/peer-group)" {
							error-message "You may not configure global route-map export for a neighbor in peer-group\n";
						}
					}
				}
				container address-family {
					description "Parameters relating to IPv4 or IPv6 routes";
					presence "Enables BGP neighbor address-family";
					configd:help "Parameters relating to IPv4 or IPv6 routes";
					container ipv4-unicast {
						description "BGP neighbor parameters";
						presence "Enables BGP neighbor IPv4 parameters";
						configd:help "BGP neighbor parameters";
						uses peer-grp-neighbor-afi-common-settings {
							refine filter-list/export {
								must "not(../../peer-group)" {
									error-message "You may not configure filter-list export for a neighbor in peer-group\n";
								}
							}
							refine route-map/export {
								must "not(../../peer-group)" {
									error-message "You may not configure route-map export for a neighbor in peer-group\n";
								}
							}
							refine attribute-unchanged {
								must "not(../peer-group)" {
									error-message "You may not configure attribute-unchanged for a neighbor in peer-group\n";
								}
							}
							refine remove-private-as {
								must "not(../peer-group)" {
									error-message "You may not configure remove-private-as for a neighbor in peer-group\n";
								}
							}
							refine route-reflector-client {
								must "not(../peer-group)" {
									error-message "You may not configure route-reflector-client for a neighbor in peer-group\n";
								}
							}
							refine disable-send-community {
								must "not(../peer-group)" {
									error-message "You may not configure disable-send-community for a neighbor in peer-group\n";
								}
							}
							refine capability/orf {
								must "not(../../peer-group)" {
									error-message "You may not configure capability orf for a neighbor in peer-group";
								}
							}
							refine default-originate {
								must "not(../peer-group)" {
									error-message "You may not configure default-originate for a neighbor in peer-group\n";
								}
							}
							refine unsuppress-map {
								must "not(../peer-group)" {
									error-message "You may not configure unsuppress-map for a neighbor in peer-group\n";
								}
							}
							refine nexthop-self {
								must "not(../peer-group)" {
									error-message "You may not configure nexthop-self for a neighbor in peer-group\n";
								}
							}
							refine route-server-client {
								must "not(../peer-group)" {
									error-message "You may not configure route-server-client for a neighbor in peer-group\n";
								}
							}
						}
						uses neigh_peer_grp_ipv4_lists {
							refine distribute-list {
								must "not(../../../../peer-group[tagnode = current()/../peer-group]/address-family/ipv4-unicast/prefix-list)" {
									error-message "You may not configure distribute-list when prefix-list is set in peer-group";
								}
							}
							refine prefix-list {
								must "not(../../../../peer-group[tagnode = current()/../peer-group]/address-family/ipv4-unicast/distribute-list)" {
									error-message "You may not configure prefix-list when distribute-list is set in peer-group";
								}
							}
						}
						leaf peer-group {
							description "IPv4 peer group for this peer";
							type leafref {
							    path "../../../../peer-group/tagnode";
							}
							configd:help "IPv4 peer group for this peer";
							must "../../../../peer-group[tagnode=current()]/address-family/ipv4-unicast" {
								error-message 'You must configure address-family ipv4-unicast in peer-group';
							}
							configd:validate "/opt/vyatta/share/tmplscripts/protocols/bgp/neighbor/address-family/peer-group/configd_update.cli";
						}
					}
					container ipv6-unicast {
						description "BGP neighbor parameters";
						presence "Enables BGP neighbor IPv6 parameters";
						configd:help "BGP neighbor parameters";
						uses peer-grp-neighbor-afi-common-settings {
							refine filter-list/export {
								must "not(../../peer-group)" {
									error-message "You may not configure filter-list export for a neighbor in peer-group\n";
								}
							}
							refine route-map/export {
								must "not(../../peer-group)" {
									error-message "You may not configure route-map export for a neighbor in peer-group\n";
								}
							}
							refine attribute-unchanged {
								must "not(../peer-group)" {
									error-message "You may not configure attribute-unchanged for a neighbor in peer-group\n";
								}
							}
							refine remove-private-as {
								must "not(../peer-group)" {
									error-message "You may not configure remove-private-as for a neighbor in peer-group\n";
								}
							}
							refine route-reflector-client {
								must "not(../peer-group)" {
									error-message "You may not configure route-reflector-client for a neighbor in peer-group\n";
								}
							}
							refine disable-send-community {
								must "not(../peer-group)" {
									error-message "You may not configure disable-send-community for a neighbor in peer-group\n";
								}
							}
							refine capability/orf {
								must "not(../../peer-group)" {
									error-message "You may not configure capability orf for a neighbor in peer-group";
								}
							}
							refine default-originate {
								must "not(../peer-group)" {
									error-message "You may not configure default-originate for a neighbor in peer-group\n";
								}
							}
							refine unsuppress-map {
								must "not(../peer-group)" {
									error-message "You may not configure unsuppress-map for a neighbor in peer-group\n";
								}
							}
							refine nexthop-self {
								must "not(../peer-group)" {
									error-message "You may not configure nexthop-self for a neighbor in peer-group\n";
								}
							}
							refine route-server-client {
								must "not(../peer-group)" {
									error-message "You may not configure route-server-client for a neighbor in peer-group\n";
								}
							}
						}
						uses neigh_peer_grp_ipv6_lists {
							refine distribute-list {
								must "not(../../../../peer-group[tagnode = current()/../peer-group]/address-family/ipv6-unicast/prefix-list)" {
									error-message "You may not configure distribute-list when prefix-list is set in peer-group";
								}
							}
							refine prefix-list {
								must "not(../../../../peer-group[tagnode = current()/../peer-group]/address-family/ipv6-unicast/distribute-list)" {
									error-message "You may not configure distribute-list when distribute-list is set in peer-group";
								}
							}
						}
						leaf peer-group {
							description "IPv6 peer group for this peer";
							type leafref {
							    path "../../../../peer-group/tagnode";
							}
							must "../../../../peer-group[tagnode=current()]/address-family/ipv6-unicast" {
								error-message "Please set address-family ipv6-unicast in peer-group";
							}
							configd:help "IPv6 peer group for this peer";
						}
					}
				}
			}
	}

	grouping bgp-params-address-family {
			container address-family {
				description "BGP address-level configuration parameters";
				presence "Enables BGP address-family parameter";
				configd:help "BGP address-family parameters";
				container ipv4-unicast {
					description "BGP IPv4 settings";
					presence "Enables BGP IPv4 settings";
					configd:help "BGP IPv4 settings";
					container parameters {
						description "BGP parameters for the ipv4-unicast address family";
						presence "Enables BGP parameters for the ipv4-unicast address family";
						configd:help "BGP parameters for the ipv4-unicast address family";
						leaf synchronization {
							description "Enable BGP synchronization for the ipv4-unicast address family";
							type empty;
							configd:help "Enable BGP synchronization for the ipv4-unicast address family";
						}
						leaf network-synchronization {
							description "Enable BGP network synchronization for the ipv4-unicast address family";
							type empty;
							configd:help "Enable BGP network synchronization for the ipv4-unicast address family";
						}
						uses parameters-distance;
						uses parameters-dampening;
					}
					uses ipv4-aggregate-address;
					uses network-ipv4;
					uses redistribute-ipv4;
					leaf auto-summary {
						description "Enable automatic network number summarization";
						type empty;
						configd:help "Enable automatic network number summarization";
					}
					uses bgp-nexthop-rmap;
				}
				container ipv6-unicast {
					description "Enable BGP IPv6 settings";
					presence "Enables BGP IPv6 settings";
					configd:help "BGP IPv6 settings";
					container parameters {
						description "BGP parameters for the ipv6-unicast address family";
						presence "Enables BGP parameters for the ipv6-unicast address family";
						configd:help "BGP parameters for the ipv6-unicast address family";
						leaf synchronization {
							description "Enable BGP synchronization for the ipv6-unicast address family";
							type empty;
							configd:help "Enable BGP synchronization for the ipv6-unicast address family";
						}
						leaf network-synchronization {
							description "Enable BGP network synchronization for the ipv6-unicast address family";
							type empty;
							configd:help "Enable BGP network synchronization for the ipv6-unicast address family";
						}
						uses parameters-distance;
						uses parameters-dampening;
					}
					uses ipv6-aggregate-address;
					uses network-ipv6;
					uses redistribute-ipv6;
					leaf auto-summary {
						description "Enable automatic network number summarization";
						type empty;
						configd:help "Enable automatic network number summarization";
					}
					uses bgp-nexthop-rmap;
				}
			}
	}

	grouping bgp-protocol {
		list bgp {
			configd:priority "710";
			description "BGP configuration parameters";
			configd:help "Border Gateway Protocol (BGP) parameters";
			configd:end "/opt/vyatta/share/tmplscripts/protocols/bgp/configd_end.sh";
			must "(tagnode != 23456)" {
				error-message "Invalid AS Number, 23456 (Reserved)";
			}
			must "((tagnode <=  65535) or " +
                "(/protocols:protocols/vyatta-protocols-bgp-v1:bgp/vyatta-protocols-bgp-v1:parameters/vyatta-protocols-bgp-v1:extended-asn-capability))" {
				error-message "Extended ASN Capability must be enabled for configuring ASN greater than 65535";
			}
			must "count(../bgp/tagnode) <= 1" {
				error-message "Another BGP instance is already running" ;
			}
			key "tagnode";
			leaf tagnode {
				description "BGP AS Number";
				type uint32 {
					range 1..max;
				}
				configd:help "Border Gateway Protocol (BGP) parameters";
			}

		uses bgp-params-global-default-vrf;
		uses bgp-params-peer-group;
		uses bgp-params-neighbor {
			refine neighbor {
				configd:validate "/opt/vyatta/share/tmplscripts/protocols/bgp/neighbor/configd_validate.sh";
			}
		}
		uses bgp-params-address-family;
		uses bgp-params-log;
		}
	}

	/* Augmenting to protocols - default VRF */
	augment /protocols:protocols {
		uses bgp-protocol;
	}

	/* Augmenting trap notifications */
	augment /service:service/service-snmp:snmp/service-snmp:notification {
		container bgp {
			description "BGP Notifications";
			configd:help "BGP Notifications";
			leaf all {
				description "Enable BGP Notifications";
				type empty;
				configd:help "BGP Notifications";
				configd:create "vtysh -c \"configure terminal\" -c \"bgp notification all\"";
				configd:delete "vtysh -c \"configure terminal\" -c \"no bgp notification\"";
			}
		}
	}
}
