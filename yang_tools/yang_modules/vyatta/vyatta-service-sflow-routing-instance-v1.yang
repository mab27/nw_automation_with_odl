module vyatta-service-sflow-routing-instance-v1 {
	namespace "urn:vyatta.com:mgmt:vyatta-service-sflow-routing-instance:1";
	prefix vyatta-service-sflow-routing-instance-v1;

	import vyatta-services-v1 {
		prefix service;
	}
	import configd-v1 {
		prefix configd;
	}
	import vyatta-service-sflow-v1 {
		prefix sflow;
	}
	import vyatta-routing-v1 {
		prefix rd;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-service-sflow-routing-instance-v1";

	revision 2016-01-13 {
		description "Initial revision of version 1.";
	}

	augment /service:service/sflow:sflow/sflow:server-address {
		leaf routing-instance {
			type leafref {
				path "/rd:routing/rd:routing-instance/rd:instance-name";
			}
			configd:help "Routing Domain used to export packets to collector";
		}
	}
}
