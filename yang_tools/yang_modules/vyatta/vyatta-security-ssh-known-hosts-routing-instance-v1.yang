module vyatta-security-ssh-known-hosts-routing-instance-v1 {
	namespace "urn:vyatta.com:mgmt:vyatta-security-ssh-known-hosts-routing-instance:1";
	prefix vyatta-security-ssh-known-hosts-routing-instance-v1;

	import vyatta-security-ssh-known-hosts-v1 {
		prefix known-hosts;
	}
	import vyatta-routing-v1 {
		prefix rt-instance;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communication Systems, Inc.
		 All rights reserved.

		 routing-instance SSH known hosts configuration";

	revision 2016-04-13 {
		description "Initial revision of version 1.";
	}

	augment /rt-instance:routing/rt-instance:routing-instance/rt-instance:security {
		uses known-hosts:ssh-known-host {
			refine ssh-known-hosts {
				configd:end "/opt/vyatta/share/tmplscripts/security/ssh-known-hosts/configd_vrf_end.sh $VAR(../../@)";
			}
		}
	}
}
