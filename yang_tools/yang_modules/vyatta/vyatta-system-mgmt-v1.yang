module vyatta-system-mgmt-v1 {
	namespace "urn:vyatta.com:mgmt:vyatta-system-mgmt:1";
	prefix vyatta-system-mgmt-v1;

	import vyatta-system-v1 {
		prefix system;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 The YANG module for vyatta-system-mgmt-v1";

	revision 2016-03-17 {
		description "Move commit-archive to grouping.";
	}
	revision 2015-12-04 {
		description "Convert comp_help extension to description.";
	}
	revision 2015-08-14 {
		description "Initial revision of version 1.";
	}
	
	grouping cfg-mgt-commit-archive-group {
		container commit-archive {
			presence
			  "Enables config commit archive to remote locations";
			description "Remote locations for archived config commit";
			configd:priority "400";
			configd:help "Commit archival settings";
			configd:end "/opt/vyatta/share/tmplscripts/system/config-management/commit-archive/configd_end.sh";
			leaf-list location {
				description "Location of commit archive

					     URLs supported are:
					      - scp://<user>:<passwd>@<host>/<dir>
					      - ftp://<user>:<passwd>@<host>/<dir>
					      - tftp://<host>/<dir>";
				type string {
					pattern '(tftp|ftp|scp)://.*/.*' {
						error-message "URL scheme must one of tftp, ftp, scp";
					}
				}
				ordered-by "user";
				configd:help "Commit archive location";
			}
		}
	}

	augment /system:system {
		container config-management {
			presence "true";
			configd:help "Configuration management settings";
			uses cfg-mgt-commit-archive-group;
			leaf commit-revisions {
				type uint32 {
					range 0..65535 {
						error-message "Commit revisions must be in range 0 to 65535";
					}
				}
				configd:priority "400";
				configd:help "Commit revisions";
				configd:update "/opt/vyatta/share/tmplscripts/system/config-management/commit-revisions/configd_update.sh";
				configd:delete "/opt/vyatta/share/tmplscripts/system/config-management/commit-revisions/configd_delete.sh";
			}
		}
	}
}
