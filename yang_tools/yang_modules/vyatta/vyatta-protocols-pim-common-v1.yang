module vyatta-protocols-pim-common-v1 {
	namespace "urn:vyatta.com:mgmt:vyatta-protocols-pim-common:1";
	prefix vyatta-protocols-pim-common-v1;

	import configd-v1 {
		prefix configd;
	}
	import vyatta-interfaces-v1 {
		prefix if;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 The YANG module for vyatta-protocols-pim-common-v1";

	revision 2016-06-02 {
		description "Initial revision";
	}

	grouping interface-leaf {
		leaf interface {
			must "current() = /if:interfaces/*/*[(local-name(.) = 'tagnode') or (local-name(.) = 'ifname')] " +
				 "or /if:interfaces/*/*[local-name(.) = 'vif'][./../* = substring-before(current(), '.')]" +
					"/*[(local-name(.) = 'tagnode') or (local-name(.) = 'ifname')]" +
					"[. = substring-after(current(), '.')] " +
				 "or /if:interfaces/*/*[local-name(.) = 'vrrp']/*[local-name(.) = 'vrrp-group']" +
					"[./../../* = substring-before(current(), 'v')]" +
					"/*[local-name(.) = 'tagnode'][. = substring-after(current(), 'v')] " +
				 "or /if:interfaces/*/*[local-name(.) = 'vif'][./../* = substring-before(current(), '.')]" +
					"/*[(local-name(.) = 'tagnode') or (local-name(.) = 'ifname')]" +
					"[. = substring-after(substring-before(current(), 'v'), '.')]" +
					"/../*[local-name(.) = 'vrrp']/*[local-name(.) = 'vrrp-group']" +
					"/*[local-name(.) = 'tagnode'][. = substring-after(current(), 'v')]" {
				error-message "Interface does not exist on this system";
			}
			type string;
			configd:help "Interface name";
			configd:allowed "/opt/vyatta/share/tmplscripts/protocols/pim/interface_allowed.sh";
		}
	}

    grouping interface-tagnode {
		leaf tagnode {
			must "current() = /if:interfaces/*/*[(local-name(.) = 'tagnode') or (local-name(.) = 'ifname')] " +
				 "or /if:interfaces/*/*[local-name(.) = 'vif'][./../* = substring-before(current(), '.')]" +
					"/*[(local-name(.) = 'tagnode') or (local-name(.) = 'ifname')]" +
					"[. = substring-after(current(), '.')] " +
				 "or /if:interfaces/*/*[local-name(.) = 'vrrp']/*[local-name(.) = 'vrrp-group']" +
					"[./../../* = substring-before(current(), 'v')]" +
					"/*[local-name(.) = 'tagnode'][. = substring-after(current(), 'v')] " +
				 "or /if:interfaces/*/*[local-name(.) = 'vif'][./../* = substring-before(current(), '.')]" +
					"/*[(local-name(.) = 'tagnode') or (local-name(.) = 'ifname')]" +
					"[. = substring-after(substring-before(current(), 'v'), '.')]" +
					"/../*[local-name(.) = 'vrrp']/*[local-name(.) = 'vrrp-group']" +
					"/*[local-name(.) = 'tagnode'][. = substring-after(current(), 'v')]" {
				error-message "Interface does not exist on this system";
			}
			type string;
			configd:help "Interface name";
			configd:allowed "/opt/vyatta/share/tmplscripts/protocols/pim/interface_allowed.sh";
		}
	}
}
