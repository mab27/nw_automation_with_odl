module vyatta-service-snmp-routing-instance-v1 {
	namespace "urn:vyatta.com:mgmt:vyatta-service-snmp-routing-instance:1";
	prefix vyatta-service-snmp--routing-instance-v1;

	import vyatta-services-v1 {
		prefix service;
	}
	import configd-v1 {
		prefix configd;
	}
	import vyatta-service-snmp-v1 {
		prefix snmp;
	}
	import vyatta-routing-v1 {
		prefix vyatta-routing;
	}

	organization "Brocade Communications Systems, Inc.";
	contact
		"Brocade Communications Systems, Inc.
		 Postal: 130 Holger Way
		         San Jose, CA 95134
		 E-mail: support@Brocade.com
		 Web: www.brocade.com";

	description
		"Copyright (c) 2016 by Brocade Communications Systems, Inc.
		 All rights reserved.

		 SNMP routing-instance configuration";

	revision 2016-03-07 {
		description "Added support for VRF-aware SNMP.";
	}

	grouping routing-instance-group {
		leaf routing-instance {
			description "This leaf is used to associate a routing-instance with trap-target,
				     allowing VRF specific traps to be sent to specific trap receivers.";
			configd:help "Specifies the routing-instance for trap-target";
			type leafref {
				path "/vyatta-routing:routing/vyatta-routing:routing-instance/vyatta-routing:instance-name";
			}
		}
	}

	augment /service:service/snmp:snmp/snmp:trap-target {
		uses routing-instance-group {
			refine routing-instance {
				configd:help "Specifies routing-instance for SNMPv2 trap-target, default otherwise";
			}
		}
	}
	augment /service:service/snmp:snmp/snmp:community {
		leaf context {
			description "This leaf is used to map a context to SNMP v1/v2c community string.";
			configd:help "Defines the name of the routing instance";
			type leafref {
				path "/vyatta-routing:routing/vyatta-routing:routing-instance/vyatta-routing:instance-name";
			}
		}
	}
	augment /service:service/snmp:snmp/snmp:v3/snmp:trap-target {
		uses routing-instance-group {
			refine routing-instance {
				configd:help "Specifies routing-instance for SNMPv3 trap-target, default otherwise";
			}
		}
	}
	augment /service:service/snmp:snmp {
		leaf-list routing-instance {
			description "This leaf specifies the routing-instance SNMP agent is listening
					on for incoming SNMP requests.";
			configd:help "Specifies the routing-instance to listen on for SNMP requests";
			max-elements "1";
			type leafref {
				path "/vyatta-routing:routing/vyatta-routing:routing-instance/vyatta-routing:instance-name";
			}
		}
	}
}
