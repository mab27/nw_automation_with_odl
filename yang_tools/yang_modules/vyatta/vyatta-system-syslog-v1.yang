module vyatta-system-syslog-v1 {
	namespace "urn:vyatta.com:mgmt:vyatta-system-syslog:1";
	prefix vyatta-system-syslog-v1;

	import vyatta-types-v1 {
		prefix types;
	}
	import vyatta-system-v1 {
		prefix system;
	}
	import configd-v1 {
		prefix configd;
	}

	organization "Brocade Communications Systems, Inc.";
	contact
		"Brocade Communications Systems, Inc.
		 Postal: 130 Holger Way
		         San Jose, CA 95134
		 E-mail: support@Brocade.com
		 Web: www.brocade.com";

	description
		"Copyright (c) 2014-2016 by Brocade Communications Systems, Inc.
		 All rights reserved.

		 Syslog configuration";

	revision 2016-11-16 {
		description "Add help text where missing";
	}

	revision 2016-09-21 {
		description "Add 'rate-limit' configuration commands";
	}

	revision 2016-08-15 {
		description "Remove 'all' option from facility-override";
	}

	revision 2016-04-22 {
		description "Reorganization for modularity";
	}
        
	revision 2015-08-14 {
		description "Initial revision of version 1.";
	}

	typedef remote-host {
		type union {
			type types:hostname-port;
			type types:ipv4-addr-port;
			type types:ipv6-addr-port;
		}
	}

	typedef facility {
		type enumeration {
			enum "auth" {
				configd:help "Authentication and authorization";
			}
			enum "authpriv" {
				configd:help "Non-system authorization";
			}
			enum "cron" {
				configd:help "Cron daemon";
			}
			enum "dataplane" {
				configd:help "Dataplane (local6)";
			}
			enum "daemon" {
				configd:help "System daemons";
			}
			enum "kern" {
				configd:help "Kernel";
			}
			enum "lpr" {
				configd:help "Line printer spooler";
			}
			enum "mail" {
				configd:help "Mail subsystem";
			}
			enum "mark" {
				configd:help "Timestamp";
			}
			enum "news" {
				configd:help "USENET subsystem";
			}
			enum "protocols" {
				configd:help "Routing protocols (local7)";
			}
			enum "security" {
				configd:help "Authentication and authorization";
			}
			enum "sensors" {
				configd:help "Hardware sensors";
			}
			enum "syslog" {
				configd:help "Authentication and authorization";
			}
			enum "user" {
				configd:help "Application processes";
			}
			enum "uucp" {
				configd:help "UUCP subsystem";
			}
			enum "local0" {
				configd:help "Local facility 0";
			}
			enum "local1" {
				configd:help "Local facility 1";
			}
			enum "local2" {
				configd:help "Local facility 2";
			}
			enum "local3" {
				configd:help "Local facility 3";
			}
			enum "local4" {
				configd:help "Local facility 4";
			}
			enum "local5" {
				configd:help "Local facility 5";
			}
			enum "local6" {
				configd:help "Local facility 6";
			}
			enum "local7" {
				configd:help "Local facility 7";
			}
			enum "all" {
				configd:help "All facilities excluding \"mark\"";
			}
		}
	}


	typedef facility-no-all {
		type enumeration {
			enum "auth" {
				configd:help "Authentication and authorization";
			}
			enum "authpriv" {
				configd:help "Non-system authorization";
			}
			enum "cron" {
				configd:help "Cron daemon";
			}
			enum "dataplane" {
				configd:help "Dataplane (local6)";
			}
			enum "daemon" {
				configd:help "System daemons";
			}
			enum "kern" {
				configd:help "Kernel";
			}
			enum "lpr" {
				configd:help "Line printer spooler";
			}
			enum "mail" {
				configd:help "Mail subsystem";
			}
			enum "mark" {
				configd:help "Timestamp";
			}
			enum "news" {
				configd:help "USENET subsystem";
			}
			enum "protocols" {
				configd:help "Routing protocols (local7)";
			}
			enum "security" {
				configd:help "Authentication and authorization";
			}
			enum "sensors" {
				configd:help "Hardware sensors";
			}
			enum "syslog" {
				configd:help "Authentication and authorization";
			}
			enum "user" {
				configd:help "Application processes";
			}
			enum "uucp" {
				configd:help "UUCP subsystem";
			}
			enum "local0" {
				configd:help "Local facility 0";
			}
			enum "local1" {
				configd:help "Local facility 1";
			}
			enum "local2" {
				configd:help "Local facility 2";
			}
			enum "local3" {
				configd:help "Local facility 3";
			}
			enum "local4" {
				configd:help "Local facility 4";
			}
			enum "local5" {
				configd:help "Local facility 5";
			}
			enum "local6" {
				configd:help "Local facility 6";
			}
			enum "local7" {
				configd:help "Local facility 7";
			}
			enum "all" {
				status obsolete;
				configd:help "All facilities excluding \"mark\"";
			}
		}
	}

	typedef level {
		type enumeration {
			enum "emerg" {
				configd:help "Emergency messages";
			}
			enum "alert" {
				configd:help "Urgent messages";
			}
			enum "crit" {
				configd:help "Critical messages ";
			}
			enum "err" {
				configd:help "Error messages";
			}
			enum "warning" {
				configd:help "Warning messages";
			}
			enum "notice" {
				configd:help "Messages for further investigation";
			}
			enum "info" {
				configd:help "Informational messages";
			}
			enum "debug" {
				configd:help "Debug messages";
			}
		}
	}

	grouping facility {
		list facility {
			configd:help "Facility for system logging";
			key "tagnode";
			leaf tagnode {
				type facility;
				configd:help "Facility for system logging";
				description "Specifies a log facility value.";
			}
			leaf level {
				type level;
				configd:help "Logging level";
				default "err";
				configd:create "/opt/vyatta/share/tmplscripts/system/syslog/global/facility/level/configd_create.sh";
				configd:delete "/opt/vyatta/share/tmplscripts/system/syslog/global/facility/level/configd_delete.sh";
				description "Specifies a log level value.";
			}
			description "List of facility and level values.";
		}
	}

	grouping archive {
		container archive {
			configd:help "Log file size and rotation characteristics";
			leaf files {
				type uint32 {
					configd:help "Number of saved files";
				}
				configd:help "Number of saved files";
				default "5";
				description "Specifies the number of retained log files. The
					     oldest log files are deleted if this number is
					     exceeded.";
			}
			leaf size {
				type uint32 {
					configd:help "Size of log files (kbytes)";
				}
				configd:help "Size of log files (kbytes)";
				default "250";
				description "Specifies the maximum size of the log file. If
					     this size is exceeded the current log file
					     will be archived and a new log file created.";
			}
			description "Configures the maximum size and the maximum number of
				     retained log files. When the maximum size is reached
				     the current log file is archived and a new log file is
				     created. If the maximum number of log files is exceeded
				     by creating the new log file the oldest log file will
				     be deleted."; 
		}
	}

	grouping syslog-rate-limit {
		container rate-limit {
			description "Configures the maximum burst size (in number of log entries)
				     allowed within the interval specified. Log entries will be 
				     suppressed if the number of log entries exceeds the
				     burst value within the specified interval.";
			presence "Enable rate-limit";
			configd:help "Enable log rate limiting";
			leaf interval {
				type types:time-interval-seconds;
				configd:help "Interval in seconds";
				default "5";
				description "Specifies the rate limit interval in seconds. 
					     If the number of log entries exceeds the burst
					     value within this interval logging will be
					     suppressed.";
			}
			leaf burst {
				type uint32 {
					configd:help "Number of log entries in interval";
				}
				configd:help "Number of log entries in interval";
				default "200";
				description "Specifies the maximum number of log entries
					     allowed within the specified interval before
					     logs are suppressed";
			}
		}
	}

	grouping facility-archive {
		uses facility;
		uses archive;
	}

	grouping syslog-base {
		container syslog {
			presence "Enable syslog";
			configd:priority "400";
			configd:help "System logging daemon";
			configd:end "/opt/vyatta/share/tmplscripts/system/syslog/configd_end.sh";
			description "Configures system logging destinations.";
		}
	}

	grouping syslog-global {
		container global {
			presence "Enable global";
			configd:help "Logging to system standard location";
			configd:validate "/opt/vyatta/share/tmplscripts/system/syslog/global/configd_validate1.cli";
			uses facility-archive;
			description "Configures system standard log file attributes including
				     facility, level, maximum number of log files, and
				     the maximum size of the log file.";
		}
	}

	grouping syslog-remote {
		list host {
			configd:help "Logging to a remote host";
			configd:validate "/opt/vyatta/share/tmplscripts/system/syslog/host/configd_validate1.cli";
			key "tagnode";
			leaf tagnode {
				type remote-host;
			}
			uses facility;
			leaf facility-override {
				description "Override replaces facility field in all logs to host.";
				type facility-no-all;
				configd:help "Override replaces log entry facility field";
			}
			description "Configures a remote host as the destination for log entries.
				     Log entries that match the specified facility and level values
				     will be sent to the system console.";
		}
	}

	grouping syslog-local {
		list file {
			configd:help "Logging to a file";
			configd:validate "/opt/vyatta/share/tmplscripts/system/syslog/file/configd_validate1.cli";
			key "tagnode";
			leaf tagnode {
				type string {
					pattern '[-a-zA-Z0-9_.]+' {
						configd:error-message "invalid file name $VAR(@)";
					}
				}
				configd:help "Logging to a file";
				description "Name of the file to be used as a logging destination.";
			}
			uses facility-archive;
			description "Configures a file as the destination for logging entries.
				     The file is created in /var/log/user. Log entries that match
				     the specified facility and level values will be sent to the
				     system console.";
		}
		list user {
			configd:help "Logging to specific user's terminal";
			configd:validate "/opt/vyatta/share/tmplscripts/system/syslog/user/configd_validate1.cli";
			key "tagnode";
			leaf tagnode {
				type string {
					pattern '[a-zA-Z_][a-zA-Z0-9_-]*' {
						configd:error-message "invalid user name $VAR(@)";
					}
				}
				configd:help "Logging to specific user's terminal";
				description "Logging will be sent to the user's terminal indicated
					     by this username.";
			}
			uses facility;
			description "Configures a logged in users terminal as a destination for
				     logging entries. Log entries that match the specified facility
				     and level values will be sent to the system console.";

		}
		container console {
			presence "Enable console";
			configd:help "Logging to system console";
			configd:validate "/opt/vyatta/share/tmplscripts/system/syslog/console/configd_validate1.cli";
			uses facility;
			description "Configures the system console as a destination for logging entries.
				     Log entries that match the specified facility and level values
				     will be sent to the system console.";

		}

	}

	augment /system:system {
		uses syslog-base;
	}

	augment /system:system/syslog {
		uses syslog-global;
		uses syslog-remote;
		uses syslog-local;
		uses syslog-rate-limit;
	}

}
